;;; AxisBuilder v5.0 - One Generated Layered Drawing
;;; Generated from Excel on 2026-10-22 16:25:48
;;; Load in DraftSight with APPLOAD/LOADAPPLICATION, then type AXISBUILDER.

(setq SL_CAD_PLATFORM "DRAFTSIGHT")
(setq SL_HATCH_TRANSPARENCY 50)

(defun SL_pt (x y)
  ;; Normalize signed zero before constructing a CAD point.
  (if (< (abs x) 0.0000001) (setq x 0.0))
  (if (< (abs y) 0.0000001) (setq y 0.0))
  (strcat (rtos x 2 3) "," (rtos y 2 3))
)

(defun SL_tf_x (x y)
  (cond
    ((= SL_ORIENTATION "Vertical") x)
    ((= SL_ORIENTATION "Horizontal CW") y)
    ((= SL_ORIENTATION "Horizontal CCW") (- y))
    (T y)
  )
)

(defun SL_tf_y (x y)
  (cond
    ((= SL_ORIENTATION "Vertical") y)
    ((= SL_ORIENTATION "Horizontal CW") (- x))
    ((= SL_ORIENTATION "Horizontal CCW") x)
    (T (- x))
  )
)

(defun SL_rot (base)
  (cond
    ((= SL_ORIENTATION "Vertical") base)
    ((= SL_ORIENTATION "Horizontal CW") (- base 90))
    ((= SL_ORIENTATION "Horizontal CCW") (+ base 90))
    (T (- base 90))
  )
)

(defun SL_Layer (name color)
  (command "-LAYER" "M" name "C" (itoa color) "" "")
)

;; Hatch lines are drawn ByLayer, so layer transparency (0-90) controls them.
;; Reapplied on every run so existing layers pick up the current setting.
(defun SL_SetLayerTransparency (layers / result ok act)
  (setq result (vl-catch-all-apply 'command (list "_.-LAYER" "_Transparency" (itoa SL_HATCH_TRANSPARENCY) layers "")))
  (setq ok (not (vl-catch-all-error-p result)))
  ;; If -LAYER is still waiting for input, cancel it so generation can continue.
  (setq act (getvar "CMDACTIVE"))
  (if (and act (> (logand act 3) 0)) (progn (command) (setq ok nil)))
  (if (not ok) (princ "\nAxisBuilder: hatch layer transparency could not be set (set it in the Layer Manager)."))
  (princ)
)

(defun SL_SetLayer (layer)
  ;; Fast path for AutoCAD and DraftSight: avoid repeated -LAYER commands.
  (if (and (/= layer "") (/= (strcase (getvar "CLAYER")) (strcase layer)))
    (setvar "CLAYER" layer)
  )
)

;; Set the DXF 290 layer plot flag directly for DraftSight/AutoCAD compatibility.
(defun SL_SetLayerPlottable (name shouldPlot / rec flag)
  (setq rec (tblobjname "LAYER" name) flag (if shouldPlot 1 0))
  (if rec
    (progn
      (setq rec (entget rec))
      (if (assoc 290 rec)
        (setq rec (subst (cons 290 flag) (assoc 290 rec) rec))
        (setq rec (append rec (list (cons 290 flag))))
      )
      (entmod rec)
    )
  )
)

(defun SL_SetupViewportLayers ()
  (SL_Layer "SLG_VIEWPORTS" 7)
  (SL_SetLayerPlottable "SLG_VIEWPORTS" nil)
  (SL_Layer "REPORT_VIEWPORT" 7)
  (SL_SetLayerPlottable "REPORT_VIEWPORT" T)
)

(defun SL_AssignNormalViewportsToNonPlotLayer ( / vp nextEnt ed vpNum vpLayer)
  ;; DraftSight ssget cannot reliably see VIEWPORT entities on inactive Sheets.
  ;; Walk the drawing database directly so Model-space generation can update them.
  (setq vp (entnext))
  (while vp
    (setq nextEnt (entnext vp) ed (entget vp))
    (if (= (cdr (assoc 0 ed)) "VIEWPORT")
      (progn
        (setq vpNum (cdr (assoc 69 ed)) vpLayer (cdr (assoc 8 ed)))
        ;; Number 1 is DraftSight's built-in paper-space viewport.
        ;; REPORT_VIEWPORT is intentionally printable for section reports.
        (if (and vpNum (> vpNum 1) vpLayer (/= (strcase vpLayer) "REPORT_VIEWPORT"))
          (progn
            (entmod (subst (cons 8 "SLG_VIEWPORTS") (assoc 8 ed) ed))
            (entupd vp)
          )
        )
      )
    )
    (setq vp nextEnt)
  )
)

(defun SL_AssignCurrentSheetViewports ( / ss i vp ed vpNum vpLayer moved)
  ;; DraftSight materializes/rebuilds a Sheet viewport only after that Sheet is active.
  (setq moved 0)
  (if (= (getvar "TILEMODE") 0)
    (progn
      (setq ss (ssget "_X" '((0 . "VIEWPORT"))))
      (if ss
        (progn
          (setq i 0)
          (repeat (sslength ss)
            (setq vp (ssname ss i) ed (entget vp) i (1+ i))
            (setq vpNum (cdr (assoc 69 ed)) vpLayer (cdr (assoc 8 ed)))
            (if (and vpNum (> vpNum 1) vpLayer (/= (strcase vpLayer) "REPORT_VIEWPORT"))
              (progn
                (entmod (subst (cons 8 "SLG_VIEWPORTS") (assoc 8 ed) ed))
                (entupd vp)
                (setq moved (1+ moved))
              )
            )
          )
        )
      )
    )
  )
  moved
)

(defun c:ABVIEWPORTFIX ( / moved)
  (SL_SetupViewportLayers)
  (setq moved (SL_AssignCurrentSheetViewports))
  (command "_.REGEN")
  (princ (strcat "\nAxisBuilder moved " (itoa moved) " viewport(s) to the non-print layer."))
  (princ)
)

(defun SL_SetupLayers ()
  (SL_Layer "VESSEL" 7)
  (SL_Layer "SCANS" 7)
  (SL_Layer "SCAN_IMAGES" 7)
  (SL_Layer "AUT_HATCH" 5)
  (SL_Layer "SUPPORTS" 6)
  (SL_Layer "NOZZLES" 7)
  (SL_Layer "X_AXIS" 1)
  (SL_Layer "Y_AXIS" 5)
  (SL_Layer "LEGEND" 7)
  ;; Dedicated legend sample layers prevent TEXTRESIZE from touching vessel scan geometry.
  (SL_Layer "LEGEND_SAMPLE" 7)
  (SL_Layer "LEGEND_AUT_HATCH" 5)
  (SL_Layer "LEGEND_MUT_HATCH" 3)
  (SL_Layer "MANUAL_UT_HATCH" 3)
  (SL_Layer "MUT_TEXT" 7)
  (SL_Layer "CIRC_WELDS" 7)
  (SL_Layer "LONG_SEAMS" 7)
  (SL_Layer "CENTERLINE" 7)
  (SL_Layer "TITLE_BLOCK" 7)
  (SL_Layer "HEADS" 7)
  ;; Dedicated text-only layers used by the TEXTRESIZE command.
  (SL_Layer "SCAN_TEXT" 7)
  (SL_Layer "SUPPORT_TEXT" 7)
  (SL_Layer "SHELL_NOZZLE_TEXT" 7)
  (SL_Layer "HEAD_NOZZLE_TEXT" 7)
  (SL_Layer "SHELL_MUT_TEXT" 7)
  (SL_Layer "HEAD_MUT_TEXT" 7)
  (SL_Layer "X_RULER_TEXT" 1)
  (SL_Layer "Y_RULER_TEXT" 5)
  (SL_Layer "LEGEND_TEXT" 7)
  (SL_Layer "CIRC_WELD_TEXT" 7)
  (SL_Layer "LONG_SEAM_TEXT" 7)
  (SL_Layer "TITLE_BLOCK_TEXT" 7)
  (SL_Layer "HEAD_TITLE_TEXT" 7)
  (SL_Layer "HEAD_CLOCK_TEXT" 7)
  (SL_SetLayerTransparency "AUT_HATCH,LEGEND_AUT_HATCH,LEGEND_MUT_HATCH,MANUAL_UT_HATCH")
)

(defun SL_Line (x1 y1 x2 y2 layer)
  (SL_SetLayer layer)
  (command "LINE"
    (SL_pt (SL_tf_x x1 y1) (SL_tf_y x1 y1))
    (SL_pt (SL_tf_x x2 y2) (SL_tf_y x2 y2))
    ""
  )
)

(defun SL_Rect (x y w h layer)
  (SL_SetLayer layer)
  (command "RECTANGLE"
    (SL_pt (SL_tf_x x y) (SL_tf_y x y))
    (SL_pt (SL_tf_x (+ x w) (+ y h)) (SL_tf_y (+ x w) (+ y h)))
  )
)

(defun SL_TextLayer (layer)
  ;; Maps geometry layers to dedicated text-only layers.
  (cond
    ((= layer "SCANS") "SCAN_TEXT")
    ((= layer "SUPPORTS") "SUPPORT_TEXT")
    ((= layer "NOZZLES") "SHELL_NOZZLE_TEXT")
    ((= layer "MUT_TEXT") "SHELL_MUT_TEXT")
    ((= layer "X_AXIS") "X_RULER_TEXT")
    ((= layer "Y_AXIS") "Y_RULER_TEXT")
    ((= layer "LEGEND") "LEGEND_TEXT")
    ((= layer "CIRC_WELDS") "CIRC_WELD_TEXT")
    ((= layer "LONG_SEAMS") "LONG_SEAM_TEXT")
    ((= layer "TITLE_BLOCK") "TITLE_BLOCK_TEXT")
    (T layer)
  )
)

(defun SL_Text (x y h rot txt layer / textLayer)
  (setq textLayer (SL_TextLayer layer))
  (SL_SetLayer textLayer)
  (command "-TEXT" "J" "MC"
    (SL_pt (SL_tf_x x y) (SL_tf_y x y))
    (rtos h 2 3)
    (rtos (SL_rot rot) 2 0)
    txt
  )
)

(defun SL_TextLeft (x y h rot txt layer / textLayer)
  ;; Middle-left justification for title blocks and notes.
  (setq textLayer (SL_TextLayer layer))
  (SL_SetLayer textLayer)
  (command "-TEXT" "J" "ML"
    (SL_pt (SL_tf_x x y) (SL_tf_y x y))
    (rtos h 2 3)
    (rtos (SL_rot rot) 2 0)
    txt
  )
)

(defun SL_SetTextHeightInSelection (ss newH / i ent data)
  (if ss
    (progn
      (setq i 0)
      (while (< i (sslength ss))
        (setq ent (ssname ss i))
        (setq data (entget ent))
        (if (assoc 40 data)
          (progn
            (setq data (subst (cons 40 newH) (assoc 40 data) data))
            (entmod data)
            (entupd ent)
          )
        )
        (setq i (+ i 1))
      )
    )
  )
)

(defun SL_ResizeTextLayer (layer newH / ss)
  (setq ss (ssget "_X" (list (cons 0 "TEXT,MTEXT") (cons 8 layer))))
  (SL_SetTextHeightInSelection ss newH)
  (if ss (sslength ss) 0)
)

(defun SL_TextEntityPoint (ent / data)
  (setq data (entget ent))
  (cond
    ((assoc 11 data) (cdr (assoc 11 data)))
    ((assoc 10 data) (cdr (assoc 10 data)))
    (T nil)
  )
)

(defun SL_TextEntityY (ent / p)
  (setq p (SL_TextEntityPoint ent))
  (if p (cadr p) 0.0)
)

(defun SL_SetTextEntityY (ent newY / data pair p newP)
  (setq data (entget ent))
  (setq pair (if (assoc 11 data) (assoc 11 data) (assoc 10 data)))
  (if pair
    (progn
      (setq p (cdr pair))
      (setq newP (list (car p) newY (if (caddr p) (caddr p) 0.0)))
      (setq data (subst (cons (car pair) newP) pair data))
      (entmod data)
      (entupd ent)
    )
  )
)

(defun SL_InsertTextByY (ent lst / y result placed item)
  (setq y (SL_TextEntityY ent))
  (setq result nil placed nil)
  (foreach item lst
    (if (and (not placed) (< y (SL_TextEntityY item)))
      (progn (setq result (append result (list ent))) (setq placed T))
    )
    (setq result (append result (list item)))
  )
  (if (not placed) (setq result (append result (list ent))))
  result
)

(defun SL_CollectLayerText (layer summaryOnly / ss i ent txt result rawTxt)
  (setq ss (ssget "_X" (list (cons 0 "TEXT,MTEXT") (cons 8 layer))))
  (setq result nil i 0)
  (if ss
    (while (< i (sslength ss))
      (setq ent (ssname ss i))
      (setq rawTxt (cdr (assoc 1 (entget ent))))
      (setq txt (if rawTxt (strcase rawTxt) ""))
      (if (or (not summaryOnly)
              (wcmatch txt "TOTAL SCANS*,COVERAGE*,ORIENTATION*,OVERLAY*"))
        (setq result (SL_InsertTextByY ent result))
      )
      (setq i (+ i 1))
    )
  )
  result
)

(defun SL_ReflowTextStack (layer newH spacingFactor summaryOnly / ents anchorY step i ent)
  ;; Keep the lowest text line fixed and re-space the remaining lines upward.
  (setq ents (SL_CollectLayerText layer summaryOnly))
  (if (> (length ents) 1)
    (progn
      (setq anchorY (SL_TextEntityY (car ents)))
      (setq step (* newH spacingFactor))
      (setq i 0)
      (foreach ent ents
        (SL_SetTextEntityY ent (+ anchorY (* i step)))
        (setq i (+ i 1))
      )
    )
  )
  (length ents)
)

(defun SL_PositionLegendSummaryBelowSamples (newH sampleBottomY / ents count step gap topY anchorY i ent)
  ;; Place the summary below the AUT/MUT samples using text-height-based clearance.
  (setq ents (SL_CollectLayerText "LEGEND_TEXT" T))
  (setq count (length ents))
  (if (> count 0)
    (progn
      (setq step (* newH 1.55))
      (setq gap (* newH 2.0))
      (setq topY (- sampleBottomY gap))
      (setq anchorY (- topY (* (- count 1) step)))
      (setq i 0)
      (foreach ent ents
        (SL_SetTextEntityY ent (+ anchorY (* i step)))
        (setq i (+ i 1))
      )
    )
  )
  count
)

(defun SL_IsLegendSummaryText (ent / raw txt)
  (setq raw (cdr (assoc 1 (entget ent))))
  (setq txt (if raw (strcase raw) ""))
  (wcmatch txt "TOTAL SCANS*,COVERAGE*,ORIENTATION*,OVERLAY*")
)

(defun SL_AddLayerToSS (layer target / src i ent)
  (setq src (ssget "_X" (list (cons 8 layer))))
  (if src
    (progn
      (setq i 0)
      (while (< i (sslength src))
        (setq ent (ssname src i))
        (if (not (ssmemb ent target)) (ssadd ent target))
        (setq i (+ i 1))
      )
    )
  )
  target
)

(defun SL_SelectionByLayers (layers / result layer)
  (setq result (ssadd))
  (foreach layer layers (SL_AddLayerToSS layer result))
  result
)

(defun SL_EntityIntersectsBounds (ent bounds / obj pmin pmax lo hi err)
  (vl-load-com)
  (setq obj (vlax-ename->vla-object ent))
  (setq err (vl-catch-all-apply 'vla-GetBoundingBox (list obj 'pmin 'pmax)))
  (if (vl-catch-all-error-p err)
    nil
    (progn
      (setq lo (vlax-safearray->list pmin))
      (setq hi (vlax-safearray->list pmax))
      (and (<= (car lo) (nth 2 bounds)) (>= (car hi) (nth 0 bounds)) (<= (cadr lo) (nth 3 bounds)) (>= (cadr hi) (nth 1 bounds)))
    )
  )
)

(defun SL_ExpandBounds (bounds pad /)
  (if bounds (list (- (nth 0 bounds) pad) (- (nth 1 bounds) pad) (+ (nth 2 bounds) pad) (+ (nth 3 bounds) pad)) nil)
)

(defun SL_SelectionByLayersInBounds (layers bounds / result layer src i ent)
  (setq result (ssadd))
  (if bounds
    (foreach layer layers
      (setq src (ssget "_X" (list (cons 8 layer))))
      (if src
        (progn
          (setq i 0)
          (while (< i (sslength src))
            (setq ent (ssname src i))
            (if (SL_EntityIntersectsBounds ent bounds) (ssadd ent result))
            (setq i (+ i 1))
          )
        )
      )
    )
  )
  result
)

(defun SL_SelectionBounds (ss / i ent obj pmin pmax lo hi minX minY maxX maxY err)
  (vl-load-com)
  (if (and ss (> (sslength ss) 0))
    (progn
      (setq i 0 minX nil minY nil maxX nil maxY nil)
      (while (< i (sslength ss))
        (setq ent (ssname ss i))
        (setq obj (vlax-ename->vla-object ent))
        (setq err (vl-catch-all-apply 'vla-GetBoundingBox (list obj 'pmin 'pmax)))
        (if (not (vl-catch-all-error-p err))
          (progn
            (setq lo (vlax-safearray->list pmin))
            (setq hi (vlax-safearray->list pmax))
            (setq minX (if minX (min minX (car lo)) (car lo)))
            (setq minY (if minY (min minY (cadr lo)) (cadr lo)))
            (setq maxX (if maxX (max maxX (car hi)) (car hi)))
            (setq maxY (if maxY (max maxY (cadr hi)) (cadr hi)))
          )
        )
        (setq i (+ i 1))
      )
      (if minX (list minX minY maxX maxY) nil)
    )
    nil
  )
)

(defun SL_SetTextEntityPoint (ent newP / data pair)
  (setq data (entget ent))
  (setq pair (if (assoc 11 data) (assoc 11 data) (assoc 10 data)))
  (if pair
    (progn
      (setq data (subst (cons (car pair) newP) pair data))
      (entmod data)
      (entupd ent)
    )
  )
)

(defun SL_ScaleLegendLabelPositions (base factor / ss i ent p newP)
  (setq ss (ssget "_X" (list (cons 0 "TEXT,MTEXT") (cons 8 "LEGEND_TEXT"))))
  (if ss
    (progn
      (setq i 0)
      (while (< i (sslength ss))
        (setq ent (ssname ss i))
        (if (not (SL_IsLegendSummaryText ent))
          (progn
            (setq p (SL_TextEntityPoint ent))
            (if p
              (progn
                (setq newP (list (+ (car base) (* (- (car p) (car base)) factor)) (+ (cadr base) (* (- (cadr p) (cadr base)) factor)) (if (caddr p) (caddr p) 0.0)))
                (SL_SetTextEntityPoint ent newP)
              )
            )
          )
        )
        (setq i (+ i 1))
      )
    )
  )
)

(defun SL_MoveLegendNonSummaryTextY (dy / ss i ent p)
  ;; Move LEGEND heading and AUT/MUT labels while leaving the four summary lines anchored.
  (setq ss (ssget "_X" (list (cons 0 "TEXT,MTEXT") (cons 8 "LEGEND_TEXT"))))
  (if (and ss (> (abs dy) 0.000001))
    (progn
      (setq i 0)
      (while (< i (sslength ss))
        (setq ent (ssname ss i))
        (if (not (SL_IsLegendSummaryText ent))
          (progn
            (setq p (SL_TextEntityPoint ent))
            (if p (SL_SetTextEntityPoint ent (list (car p) (+ (cadr p) dy) (if (caddr p) (caddr p) 0.0))))
          )
        )
        (setq i (+ i 1))
      )
    )
  )
)

(defun SL_MoveSelectionY (ss dy / i ent)
  (if (and ss (> (abs dy) 0.000001))
    (progn
      (setq i 0)
      (while (< i (sslength ss))
        (setq ent (ssname ss i))
        (command "_.MOVE" ent "" (list 0.0 0.0 0.0) (list 0.0 dy 0.0))
        (setq i (+ i 1))
      )
    )
  )
)

(defun SL_FirstTextHeight (layer / ss i data h value)
  ;; Return the smallest current height on the layer so mixed 2.0/2.3 legend text scales from the 2.0 body-text baseline.
  (setq ss (ssget "_X" (list (cons 0 "TEXT,MTEXT") (cons 8 layer))))
  (setq i 0 h nil)
  (if ss
    (while (< i (sslength ss))
      (setq data (entget (ssname ss i)))
      (setq value (cdr (assoc 40 data)))
      (if value (setq h (if h (min h value) value)))
      (setq i (+ i 1))
    )
  )
  h
)

(defun SL_ReflowRightPanelForLegend (oldH newH / factor textSS textBounds localBounds geomSS geomBounds allLegendSS before after base delta upperSS summarySS summaryBounds summaryBeforeBounds sampleGroupSS sampleGroupBounds fixedGap desiredBottom moveY i ent)
  ;; The summary stack is the fixed bottom anchor. Samples and all upper panel content grow upward.
  (if (and oldH (> oldH 0.000001) newH (> newH 0.000001))
    (progn
      (setq factor (/ newH oldH))
      (setq textSS (SL_SelectionByLayers (list "LEGEND_TEXT")))
      (setq textBounds (SL_SelectionBounds textSS))
      (setq localBounds (SL_ExpandBounds textBounds (* oldH 2.5)))
      (setq geomSS (SL_SelectionByLayersInBounds (list "LEGEND_SAMPLE" "LEGEND_AUT_HATCH" "LEGEND_MUT_HATCH") localBounds))
      (setq allLegendSS (SL_SelectionByLayersInBounds (list "LEGEND_SAMPLE" "LEGEND_AUT_HATCH" "LEGEND_MUT_HATCH" "LEGEND_TEXT") localBounds))
      (setq geomBounds (SL_SelectionBounds geomSS))
      (setq before (SL_SelectionBounds allLegendSS))
      ;; Use a deliberate fixed clearance from the top of Total Scans to the bottom of the AUT/MUT boxes.
      (setq summarySS (ssadd))
      (setq i 0)
      (if textSS
        (while (< i (sslength textSS))
          (setq ent (ssname textSS i))
          (if (SL_IsLegendSummaryText ent) (ssadd ent summarySS))
          (setq i (+ i 1))
        )
      )
      (setq summaryBeforeBounds (SL_SelectionBounds summarySS))
      (setq fixedGap 3.0)
      ;; Keep Overlay (the lowest summary line) fixed and re-space the other summary lines upward.
      (SL_ReflowTextStack "LEGEND_TEXT" newH 1.55 T)
      (if (and before geomBounds geomSS (> (sslength geomSS) 0))
        (progn
          ;; Scale the AUT/MUT sample geometry from its bottom-left corner.
          (setq base (list (nth 0 geomBounds) (nth 1 geomBounds) 0.0))
          (command "_.SCALE" geomSS "" base factor)
          (SL_ScaleLegendLabelPositions base factor)
        )
      )
      ;; Position the sample group from its true lowest visible point.
      ;; This includes the AUT/MUT captions, which extend below the sample boxes.
      (setq summaryBounds (SL_SelectionBounds summarySS))
      (setq sampleGroupSS (ssadd))
      (setq i 0)
      (if geomSS
        (while (< i (sslength geomSS))
          (ssadd (ssname geomSS i) sampleGroupSS)
          (setq i (+ i 1))
        )
      )
      (setq i 0)
      (if textSS
        (while (< i (sslength textSS))
          (setq ent (ssname textSS i))
          (if (not (SL_IsLegendSummaryText ent)) (ssadd ent sampleGroupSS))
          (setq i (+ i 1))
        )
      )
      (setq sampleGroupBounds (SL_SelectionBounds sampleGroupSS))
      (if (and summaryBounds sampleGroupBounds)
        (progn
          (setq desiredBottom (+ (nth 3 summaryBounds) fixedGap))
          (setq moveY (- desiredBottom (nth 1 sampleGroupBounds)))
          (SL_MoveSelectionY geomSS moveY)
          (SL_MoveLegendNonSummaryTextY moveY)
        )
      )
      (setq textSS (SL_SelectionByLayers (list "LEGEND_TEXT")))
      (setq textBounds (SL_SelectionBounds textSS))
      (setq localBounds (SL_ExpandBounds textBounds (* newH 2.5)))
      (setq allLegendSS (SL_SelectionByLayersInBounds (list "LEGEND_SAMPLE" "LEGEND_AUT_HATCH" "LEGEND_MUT_HATCH" "LEGEND_TEXT") localBounds))
      (setq after (SL_SelectionBounds allLegendSS))
      (setq delta (if (and before after) (- (nth 3 after) (nth 3 before)) 0.0))
      (if (> (abs delta) 0.000001)
        (progn
          (setq upperSS (SL_SelectionByLayers (list "HEADS" "HEAD_NOZZLE_TEXT" "HEAD_MUT_TEXT" "HEAD_TITLE_TEXT" "HEAD_CLOCK_TEXT" "TITLE_BLOCK" "TITLE_BLOCK_TEXT")))
          (SL_MoveSelectionY upperSS delta)
        )
      )
      delta
    )
    0.0
  )
)

(defun SL_TextLayerHeight (layer / ss ent data h mixed i h2)
  (setq ss (ssget "_X" (list (cons 0 "TEXT,MTEXT") (cons 8 layer))))
  (if (and ss (> (sslength ss) 0))
    (progn
      (setq i 0 h nil mixed nil)
      (while (< i (sslength ss))
        (setq ent (ssname ss i))
        (setq data (entget ent))
        (setq h2 (cdr (assoc 40 data)))
        (if h2
          (if (null h)
            (setq h h2)
            (if (> (abs (- h h2)) 0.000001) (setq mixed T))
          )
        )
        (setq i (+ i 1))
      )
      (cond
        (mixed "Mixed")
        (h (rtos h 2 3))
        (T "--")
      )
    )
    "--"
  )
)

(defun SL_MenuLine (num label layer)
  (princ (strcat "\n " (if (< num 10) " " "") (itoa num) "  " label "  [" (SL_TextLayerHeight layer) "]"))
)

(defun SL_TextSizeMenu ()
  (princ "\n========================================")
  (princ "\n         SCAN GENERATOR TEXT RESIZE")
  (princ "\n========================================")
  (princ "\nCurrent heights are shown in brackets.")
  (SL_MenuLine 1  "Scan IDs...................." "SCAN_TEXT")
  (SL_MenuLine 2  "Support / Object IDs........" "SUPPORT_TEXT")
  (SL_MenuLine 3  "Shell Nozzle IDs............" "SHELL_NOZZLE_TEXT")
  (SL_MenuLine 4  "Head Nozzle IDs............." "HEAD_NOZZLE_TEXT")
  (SL_MenuLine 5  "Shell MUT IDs..............." "SHELL_MUT_TEXT")
  (SL_MenuLine 6  "Head MUT IDs................" "HEAD_MUT_TEXT")
  (SL_MenuLine 7  "X-Axis ruler text..........." "X_RULER_TEXT")
  (SL_MenuLine 8  "Y-Axis ruler text..........." "Y_RULER_TEXT")
  (SL_MenuLine 9  "Legend / summary............" "LEGEND_TEXT")
  (SL_MenuLine 10 "Circ weld labels............" "CIRC_WELD_TEXT")
  (SL_MenuLine 11 "Long seam labels............" "LONG_SEAM_TEXT")
  (SL_MenuLine 12 "Title block text............" "TITLE_BLOCK_TEXT")
  (SL_MenuLine 13 "Head titles................." "HEAD_TITLE_TEXT")
  (SL_MenuLine 14 "Head clock text............." "HEAD_CLOCK_TEXT")
  (princ "\n 15  All generated text")
  (princ "\n 16  Select individual text objects")
  (princ "\n  0  Exit")
)

(defun c:TEXTRESIZE ( / choice newH oldLegendH layer layers ss count item done)
  (setq done nil)
  (while (not done)
    (SL_TextSizeMenu)
    (initget 4)
    (setq choice (getint "\nEnter option number <0>: "))
    (if (null choice) (setq choice 0))
    (cond
      ((= choice 0)
        (setq done T)
        (princ "\nTEXTRESIZE finished.")
      )
      ((and (>= choice 1) (<= choice 16))
        (initget 7)
        (setq newH (getreal "\nEnter new text height: "))
        (setq oldLegendH (if (or (= choice 9) (= choice 15)) (SL_FirstTextHeight "LEGEND_TEXT") nil))
        (if newH
          (progn
            (setq layer (cond
              ((= choice 1) "SCAN_TEXT")
              ((= choice 2) "SUPPORT_TEXT")
              ((= choice 3) "SHELL_NOZZLE_TEXT")
              ((= choice 4) "HEAD_NOZZLE_TEXT")
              ((= choice 5) "SHELL_MUT_TEXT")
              ((= choice 6) "HEAD_MUT_TEXT")
              ((= choice 7) "X_RULER_TEXT")
              ((= choice 8) "Y_RULER_TEXT")
              ((= choice 9) "LEGEND_TEXT")
              ((= choice 10) "CIRC_WELD_TEXT")
              ((= choice 11) "LONG_SEAM_TEXT")
              ((= choice 12) "TITLE_BLOCK_TEXT")
              ((= choice 13) "HEAD_TITLE_TEXT")
              ((= choice 14) "HEAD_CLOCK_TEXT")
              (T "")
            ))
            (cond
              ((<= choice 14)
                (setq count (SL_ResizeTextLayer layer newH))
              )
              ((= choice 15)
                (setq layers (list "SCAN_TEXT" "SUPPORT_TEXT" "SHELL_NOZZLE_TEXT" "HEAD_NOZZLE_TEXT" "SHELL_MUT_TEXT" "HEAD_MUT_TEXT" "X_RULER_TEXT" "Y_RULER_TEXT" "LEGEND_TEXT" "CIRC_WELD_TEXT" "LONG_SEAM_TEXT" "TITLE_BLOCK_TEXT" "HEAD_TITLE_TEXT" "HEAD_CLOCK_TEXT"))
                (setq count 0)
                (foreach item layers (setq count (+ count (SL_ResizeTextLayer item newH))))
              )
              ((= choice 16)
                (princ "\nSelect TEXT or MTEXT objects: ")
                (setq ss (ssget (list (cons 0 "TEXT,MTEXT"))))
                (setq count (if ss (sslength ss) 0))
                (SL_SetTextHeightInSelection ss newH)
              )
            )
            ;; Rebuild the right panel from the fixed legend bottom anchor.
            ;; Legend samples scale with the text, summary lines reflow, and the heads/title move by measured added height.
            (if (or (= choice 9) (= choice 15)) (SL_ReflowRightPanelForLegend oldLegendH newH))
            (if (or (= choice 12) (= choice 15)) (SL_ReflowTextStack "TITLE_BLOCK_TEXT" newH 1.75 nil))
            (command "_.REGEN")
            (princ (strcat "\nUpdated " (itoa count) " text object(s) to height " (rtos newH 2 3) "."))
            (princ "\nChoose another category, or enter 0 to exit.")
          )
        )
      )
      (T (princ "\nInvalid option. Enter a number from 0 through 16."))
    )
  )
  (princ)
)

;; ------------------------------------------------------------
;; NOZZLEWRAP - automatically wrap all shell nozzles centered on opposite rollout boundaries.
;; Click directly on the two opposite vessel rectangle edges used for circumference wrapping.
;; All CIRCLE entities on the NOZZLES layer whose centers fall on either boundary are processed.
;; Also supports left/right boundaries when the rollout is rotated.
;; ------------------------------------------------------------
(defun SL_ArcFromCircle (cdata ctr rad a1 a2 / ed item code)
  (setq ed (list (cons 0 "ARC") (cons 8 (cdr (assoc 8 cdata))) (cons 10 ctr) (cons 40 rad) (cons 50 a1) (cons 51 a2)))
  (foreach code (list 6 48 62 370 420)
    (setq item (assoc code cdata))
    (if item (setq ed (append ed (list item))))
  )
  (entmakex ed)
)

(defun SL_WrapCircleAtEdges (ent cdata ctr rad horizontal edge1 edge2 / src dst c1 c2 a1 a2 b1 b2 z)
  (setq z (if (caddr ctr) (caddr ctr) 0.0))
  (if horizontal
    (progn
      (if (<= (abs (- (cadr ctr) edge1)) (abs (- (cadr ctr) edge2)))
        (setq src edge1 dst edge2)
        (setq src edge2 dst edge1)
      )
      (setq c1 (list (car ctr) src z) c2 (list (car ctr) dst z))
      (if (< dst src)
        (setq a1 pi a2 (* 2.0 pi) b1 0.0 b2 pi)
        (setq a1 0.0 a2 pi b1 pi b2 (* 2.0 pi))
      )
    )
    (progn
      (if (<= (abs (- (car ctr) edge1)) (abs (- (car ctr) edge2)))
        (setq src edge1 dst edge2)
        (setq src edge2 dst edge1)
      )
      (setq c1 (list src (cadr ctr) z) c2 (list dst (cadr ctr) z))
      (if (> dst src)
        (setq a1 (- (/ pi 2.0)) a2 (/ pi 2.0) b1 (/ pi 2.0) b2 (* 1.5 pi))
        (setq a1 (/ pi 2.0) a2 (* 1.5 pi) b1 (- (/ pi 2.0)) b2 (/ pi 2.0))
      )
    )
  )
  (entdel ent)
  (SL_ArcFromCircle cdata c1 rad a1 a2)
  (SL_ArcFromCircle cdata c2 rad b1 b2)
  T
)

(defun c:NOZZLEWRAP ( / *error* oldOsmode p1 p2 dx dy horizontal edge1 edge2 tol ss i ent cdata ctr rad coord count)
  ;; Temporarily add Nearest object snap (OSMODE bit 512), preserving every existing snap mode.
  (setq oldOsmode (getvar "OSMODE"))
  (defun *error* (msg)
    (setvar "OSMODE" oldOsmode)
    (if (and msg (/= msg "Function cancelled") (/= msg "quit / exit abort"))
      (princ (strcat "\nNOZZLEWRAP error: " msg))
    )
    (princ)
  )
  (setvar "OSMODE" (logior oldOsmode 512))
  (setq tol 0.01)
  (setq p1 (getpoint "\nFIRST EDGE: Click the vessel rectangle TOP long edge. If the rollout is rotated, click the LEFT long edge: "))
  (if p1 (setq p2 (getpoint "\nSECOND EDGE: Click the OPPOSITE vessel rectangle BOTTOM long edge. If rotated, click the RIGHT long edge: ")))
  (cond
    ((or (null p1) (null p2)) (princ "\nNOZZLEWRAP cancelled."))
    (T
      (setq dx (abs (- (car p2) (car p1))) dy (abs (- (cadr p2) (cadr p1))))
      (if (and (< dx 0.000001) (< dy 0.000001))
        (princ "\nThe two boundary points are too close together.")
        (progn
          (setq horizontal (> dy dx))
          (if horizontal
            (setq edge1 (cadr p1) edge2 (cadr p2))
            (setq edge1 (car p1) edge2 (car p2))
          )
          (setq ss (ssget "_X" (list (cons 0 "CIRCLE") (cons 8 "NOZZLES"))))
          (setq count 0 i 0)
          (command "_.UNDO" "_Begin")
          (if ss
            (repeat (sslength ss)
              (setq ent (ssname ss i) i (1+ i) cdata (entget ent))
              (setq ctr (cdr (assoc 10 cdata)) rad (cdr (assoc 40 cdata)))
              (setq coord (if horizontal (cadr ctr) (car ctr)))
              (if (or (<= (abs (- coord edge1)) tol) (<= (abs (- coord edge2)) tol))
                (progn
                  (SL_WrapCircleAtEdges ent cdata ctr rad horizontal edge1 edge2)
                  (setq count (1+ count))
                )
              )
            )
          )
          (command "_.UNDO" "_End")
          (command "_.REGEN")
          (if (> count 0)
            (princ (strcat "\nNOZZLEWRAP complete. " (itoa count) " nozzle(s) wrapped."))
            (princ "\nNo nozzle centers were found on the selected boundaries.")
          )
        )
      )
    )
  )
  (setvar "OSMODE" oldOsmode)
  (princ)
)

;; ------------------------------------------------------------
;; ------------------------------------------------------------
;; OBJECTWRAP - split rectangular supports/objects across the circumferential rollout seam.
;; Processes only closed rectangular LWPOLYLINE entities on SUPPORTS.
;; One SUPPORT_TEXT label is retained on the larger piece; equal pieces follow the original start corner.
;; ------------------------------------------------------------
(defun SL_OWBBox (edata / minx miny maxx maxy p item)
  (foreach item edata
    (if (= (car item) 10)
      (progn
        (setq p (cdr item))
        (if (null minx)
          (setq minx (car p) maxx (car p) miny (cadr p) maxy (cadr p))
          (progn
            (setq minx (min minx (car p)) maxx (max maxx (car p)))
            (setq miny (min miny (cadr p)) maxy (max maxy (cadr p)))
          )
        )
      )
    )
  )
  (if minx (list minx miny maxx maxy) nil)
)

(defun SL_OWRectangleP (edata bb tol / count ok p item)
  (setq count 0 ok T)
  (foreach item edata
    (if (= (car item) 10)
      (progn
        (setq count (1+ count) p (cdr item))
        (if (not (and (or (equal (car p) (nth 0 bb) tol) (equal (car p) (nth 2 bb) tol))
                      (or (equal (cadr p) (nth 1 bb) tol) (equal (cadr p) (nth 3 bb) tol))))
          (setq ok nil)
        )
      )
    )
  )
  (and ok (= count 4) (> (- (nth 2 bb) (nth 0 bb)) tol) (> (- (nth 3 bb) (nth 1 bb)) tol))
)

(defun SL_OWMakeRect (x1 y1 x2 y2)
  (entmakex
    (list '(0 . "LWPOLYLINE") '(100 . "AcDbEntity") (cons 8 "SUPPORTS")
          '(100 . "AcDbPolyline") (cons 90 4) (cons 70 1)
          (cons 10 (list x1 y1)) (cons 10 (list x2 y1))
          (cons 10 (list x2 y2)) (cons 10 (list x1 y2)))
  )
)

(defun SL_OWTextPoint (edata / typ)
  (setq typ (cdr (assoc 0 edata)))
  (if (and (= typ "TEXT") (assoc 11 edata)) (cdr (assoc 11 edata)) (cdr (assoc 10 edata)))
)

(defun SL_OWFindLabel (bb tol / ss i ent ed p cx cy d best bestD)
  (setq ss (ssget "_X" (list (cons 0 "TEXT,MTEXT") (cons 8 "SUPPORT_TEXT"))))
  (setq i 0 best nil bestD nil cx (/ (+ (nth 0 bb) (nth 2 bb)) 2.0) cy (/ (+ (nth 1 bb) (nth 3 bb)) 2.0))
  (if ss
    (repeat (sslength ss)
      (setq ent (ssname ss i) i (1+ i) ed (entget ent) p (SL_OWTextPoint ed))
      (if (and p (>= (car p) (- (nth 0 bb) tol)) (<= (car p) (+ (nth 2 bb) tol))
                 (>= (cadr p) (- (nth 1 bb) tol)) (<= (cadr p) (+ (nth 3 bb) tol)))
        (progn
          (setq d (distance p (list cx cy 0.0)))
          (if (or (null bestD) (< d bestD)) (setq best ent bestD d))
        )
      )
    )
  )
  best
)

(defun SL_OWCopyLabel (label pt / ed clean item typ p3)
  (if label
    (progn
      (setq ed (entget label) clean nil typ (cdr (assoc 0 ed)))
      (foreach item ed
        (if (not (member (car item) '(-1 5 330 360))) (setq clean (cons item clean)))
      )
      (setq clean (reverse clean) p3 (list (car pt) (cadr pt) 0.0))
      (if (assoc 10 clean) (setq clean (subst (cons 10 p3) (assoc 10 clean) clean)))
      (if (and (= typ "TEXT") (assoc 11 clean)) (setq clean (subst (cons 11 p3) (assoc 11 clean) clean)))
      (entmakex clean)
    )
  )
)

(defun SL_OWCenter (r) (list (/ (+ (nth 0 r) (nth 2 r)) 2.0) (/ (+ (nth 1 r) (nth 3 r)) 2.0) 0.0))

(defun SL_OWFirstVertex (edata / item found)
  (setq found nil)
  (while (and edata (null found))
    (setq item (car edata) edata (cdr edata))
    (if (= (car item) 10) (setq found (cdr item)))
  )
  found
)

(defun SL_OWPointInRect (pt r tol)
  (and pt (>= (car pt) (- (nth 0 r) tol)) (<= (car pt) (+ (nth 2 r) tol))
          (>= (cadr pt) (- (nth 1 r) tol)) (<= (cadr pt) (+ (nth 3 r) tol)))
)

(defun SL_OWWrapRect (ent ed bb horizontal low high tol / bmin bmax overflow r1 r2 label area1 area2 target startPt startCoord mappedCoord mappedStart span)
  (setq bmin (if horizontal (nth 1 bb) (nth 0 bb)))
  (setq bmax (if horizontal (nth 3 bb) (nth 2 bb)))
  (setq r1 nil r2 nil)
  ;; Ignore objects spanning both edges or lying completely outside the rollout.
  (if (not (or (and (< bmin (- low tol)) (> bmax (+ high tol))) (<= bmax (+ low tol)) (>= bmin (- high tol))))
    (cond
      ((> bmax (+ high tol))
        (setq overflow (- bmax high))
        (if horizontal
          (setq r1 (list (nth 0 bb) (nth 1 bb) (nth 2 bb) high) r2 (list (nth 0 bb) low (nth 2 bb) (+ low overflow)))
          (setq r1 (list (nth 0 bb) (nth 1 bb) high (nth 3 bb)) r2 (list low (nth 1 bb) (+ low overflow) (nth 3 bb)))
        )
      )
      ((< bmin (- low tol))
        (setq overflow (- low bmin))
        (if horizontal
          (setq r1 (list (nth 0 bb) low (nth 2 bb) (nth 3 bb)) r2 (list (nth 0 bb) (- high overflow) (nth 2 bb) high))
          (setq r1 (list low (nth 1 bb) (nth 2 bb) (nth 3 bb)) r2 (list (- high overflow) (nth 1 bb) high (nth 3 bb)))
        )
      )
    )
  )
  (if (and r1 r2)
    (progn
      (setq label (SL_OWFindLabel bb tol))
      (SL_OWMakeRect (nth 0 r1) (nth 1 r1) (nth 2 r1) (nth 3 r1))
      (SL_OWMakeRect (nth 0 r2) (nth 1 r2) (nth 2 r2) (nth 3 r2))
      ;; Keep one ID: larger piece wins; an equal split follows the original starting corner.
      (setq area1 (* (- (nth 2 r1) (nth 0 r1)) (- (nth 3 r1) (nth 1 r1))))
      (setq area2 (* (- (nth 2 r2) (nth 0 r2)) (- (nth 3 r2) (nth 1 r2))))
      (cond
        ((> area1 (+ area2 tol)) (setq target r1))
        ((> area2 (+ area1 tol)) (setq target r2))
        (T
          (setq startPt (SL_OWFirstVertex ed) span (- high low))
          (if startPt
            (progn
              (setq startCoord (if horizontal (cadr startPt) (car startPt)) mappedCoord startCoord)
              (if (< mappedCoord low) (setq mappedCoord (+ mappedCoord span)))
              (if (> mappedCoord high) (setq mappedCoord (- mappedCoord span)))
              (if horizontal
                (setq mappedStart (list (car startPt) mappedCoord 0.0))
                (setq mappedStart (list mappedCoord (cadr startPt) 0.0))
              )
              (if (SL_OWPointInRect mappedStart r1 tol) (setq target r1) (setq target r2))
            )
            (setq target r1)
          )
        )
      )
      (SL_OWCopyLabel label (SL_OWCenter target))
      (if label (entdel label))
      (entdel ent)
      T
    )
    nil
  )
)

(defun c:OBJECTWRAP ( / *error* oldOsmode undoOpen p1 p2 dx dy horizontal edge1 edge2 low high tol ss i ent ed bb count skipped)
  (setq oldOsmode (getvar "OSMODE") undoOpen nil)
  (defun *error* (msg)
    (if undoOpen (command "_.UNDO" "_End"))
    (setvar "OSMODE" oldOsmode)
    (if (and msg (/= msg "Function cancelled") (/= msg "quit / exit abort")) (princ (strcat "\nOBJECTWRAP error: " msg)))
    (princ)
  )
  (setvar "OSMODE" (logior oldOsmode 512))
  (setq tol 0.01)
  (setq p1 (getpoint "\nFIRST EDGE: Click the vessel TOP long edge. If rotated, click the LEFT long edge: "))
  (if p1 (setq p2 (getpoint "\nSECOND EDGE: Click the opposite BOTTOM long edge. If rotated, click the RIGHT long edge: ")))
  (cond
    ((or (null p1) (null p2)) (princ "\nOBJECTWRAP cancelled."))
    (T
      (setq dx (abs (- (car p2) (car p1))) dy (abs (- (cadr p2) (cadr p1))))
      (if (and (< dx 0.000001) (< dy 0.000001))
        (princ "\nThe two boundary points are too close together.")
        (progn
          (setq horizontal (> dy dx))
          (if horizontal (setq edge1 (cadr p1) edge2 (cadr p2)) (setq edge1 (car p1) edge2 (car p2)))
          (setq low (min edge1 edge2) high (max edge1 edge2))
          (setq ss (ssget "_X" (list (cons 0 "LWPOLYLINE") (cons 8 "SUPPORTS"))))
          (setq count 0 skipped 0 i 0)
          (command "_.UNDO" "_Begin")
          (setq undoOpen T)
          (if ss
            (repeat (sslength ss)
              (setq ent (ssname ss i) i (1+ i) ed (entget ent) bb (SL_OWBBox ed))
              (if (and bb (SL_OWRectangleP ed bb tol))
                (if (SL_OWWrapRect ent ed bb horizontal low high tol) (setq count (1+ count)))
                (setq skipped (1+ skipped))
              )
            )
          )
          (command "_.UNDO" "_End")
          (setq undoOpen nil)
          (command "_.REGEN")
          (if (> count 0)
            (princ (strcat "\nOBJECTWRAP complete. " (itoa count) " support/object rectangle(s) wrapped. One ID was retained per object."))
            (princ "\nNo support/object rectangles crossed the selected boundaries.")
          )
          (if (> skipped 0) (princ (strcat "\nSkipped " (itoa skipped) " non-rectangular SUPPORTS polyline(s).")))
        )
      )
    )
  )
  (setvar "OSMODE" oldOsmode)
  (princ)
)

;; SECTIONVIEWPORTS - build equal-scale report strips on the active Sheet.
;; Run SCANLAYOUT first, then switch to a Sheet tab before using this command.
;; ------------------------------------------------------------
(defun SL_LockViewport (vp / ed flags)
  (if vp
    (progn
      (setq ed (entget vp))
      (setq flags (cdr (assoc 90 ed)))
      (if (null flags) (setq flags 0))
      (if (= 0 (logand flags 16384))
        (if (assoc 90 ed)
          (entmod (subst (cons 90 (+ flags 16384)) (assoc 90 ed) ed))
          (entmod (append ed (list (cons 90 16384))))
        )
      )
    )
  )
)

(defun SL_UnlockViewport (vp / ed flags)
  (if vp
    (progn
      (setq ed (entget vp) flags (cdr (assoc 90 ed)))
      (if (and flags (/= 0 (logand flags 16384)))
        (entmod (subst (cons 90 (- flags 16384)) (assoc 90 ed) ed))
      )
    )
  )
)

(defun SL_CreateViewport (ll ur /)
  (command "VIEWPORT" ll ur)
)
(defun SL_ActivateViewport (vp / app doc obj)
  (setvar "CVPORT" (cdr (assoc 69 (entget vp))))
)
(defun SL_ReturnPaperSpace (/ app doc)
  (setvar "CVPORT" 1)
)
(defun SL_CopySheet (source target /)
  (command "SHEET" "COPY" source target)
)
(defun SL_ActivateSheet (name /)
  (command "SHEET" "ACTIVATE" name)
)

(defun SL_SetViewportView (vp center viewHeight / ed)
  ;; Set the viewport view directly so DraftSight does not reinterpret ZOOM prompts.
  (setq ed (entget vp))
  (if (assoc 12 ed) (setq ed (subst (cons 12 center) (assoc 12 ed) ed)))
  (if (assoc 45 ed) (setq ed (subst (cons 45 viewHeight) (assoc 45 ed) ed)))
  (entmod ed)
  (entupd vp)
)

(defun SL_PaperLine (x1 y1 x2 y2 layer /)
  (SL_SetLayer layer)
  (command "LINE" (SL_pt x1 y1) (SL_pt x2 y2) "")
)

(defun SL_PaperText (x y h rot txt layer /)
  (SL_SetLayer layer)
  (command "-TEXT" "J" "MC" (SL_pt x y) (rtos h 2 6) (rtos rot 2 2) txt)
)

(defun SL_PaperTextLeft (x y h txt layer /)
  (SL_SetLayer layer)
  (command "-TEXT" "J" "ML" (SL_pt x y) (rtos h 2 6) "0" txt)
)

(defun SL_PaperRect (x y w h layer /)
  (SL_PaperLine x y (+ x w) y layer)
  (SL_PaperLine (+ x w) y (+ x w) (+ y h) layer)
  (SL_PaperLine (+ x w) (+ y h) x (+ y h) layer)
  (SL_PaperLine x (+ y h) x y layer)
)

(defun SL_PaperHatchRect (x y w h step layer / p x1 y1 x2 y2)
  (setq p (- h))
  (while (<= p w)
    (setq x1 (max 0.0 p) y1 (- x1 p) x2 (min w (+ h p)) y2 (- x2 p))
    (if (> x2 x1) (SL_PaperLine (+ x x1) (+ y y1) (+ x x2) (+ y y2) layer))
    (setq p (+ p step))
  )
)

(defun SL_PaperSectionReferences (vpLeft vpBottom vpW vpH / sc tick gap h i py txt)
  (if (= SL_SECTION_SHOW_REFS "YES")
    (progn
      (setq sc (/ vpH SL_VESSEL_XLEN) tick (* 3.0 sc) gap (* 1.5 sc) h (* 1.8 sc SL_REPORT_RULER_TEXT_SCALE) i 0)
      (foreach txt SL_SECTION_REF_LABELS
        (if (/= txt "")
          (progn
            (setq py (if (= SL_ORIENTATION "Horizontal CCW")
                       (+ vpBottom (* SL_VESSEL_XLEN (/ i 4.0) sc))
                       (- (+ vpBottom vpH) (* SL_VESSEL_XLEN (/ i 4.0) sc))))
            (SL_PaperLine (+ vpLeft vpW) py (+ vpLeft vpW tick) py "REPORT_X_REFERENCE")
            (SL_PaperTextLeft (+ vpLeft vpW tick gap) py h txt "REPORT_X_REFERENCE")
          )
        )
        (setq i (1+ i))
      )
    )
  )
)

(defun SL_PaperSectionInfo (x top u / y h boxW boxH txt)
  (if (= SL_SECTION_SHOW_TITLE "YES")
    (progn
      (setq y top)
      (SL_PaperTextLeft x y (* 0.12 u) (nth 0 SL_SECTION_TITLE_LINES) "REPORT_TITLE")
      (setq y (- y (* 0.19 u)))
      (foreach txt (cdr SL_SECTION_TITLE_LINES)
        (if (/= txt "") (progn (SL_PaperTextLeft x y (* 0.09 u) txt "REPORT_TITLE") (setq y (- y (* 0.15 u)))))
      )
    )
  )
  (if (= SL_SECTION_SHOW_LEGEND "YES")
    (progn
      (setq y (- top (* 1.40 u)) boxW (* 0.30 u) boxH (* 0.16 u))
      (SL_PaperTextLeft x y (* 0.11 u) "LEGEND" "REPORT_LEGEND")
      (setq y (- y (* 0.38 u)))
      (if (= SL_HATCH_ENABLED "YES")
        (progn
          (SL_PaperRect x y boxW boxH "REPORT_LEGEND_AUT_BOX")
          (SL_PaperHatchRect x y boxW boxH (* 0.055 u) "REPORT_LEGEND_AUT")
          (SL_PaperTextLeft (+ x (* 0.38 u)) (+ y (/ boxH 2.0)) (* 0.085 u) "AUT" "REPORT_LEGEND")
        )
      )
      (SL_PaperRect (+ x (* 0.72 u)) y boxW boxH "REPORT_LEGEND_MUT_BOX")
      (SL_PaperHatchRect (+ x (* 0.72 u)) y boxW boxH (* 0.055 u) "REPORT_LEGEND_MUT")
      (SL_PaperTextLeft (+ x (* 1.10 u)) (+ y (/ boxH 2.0)) (* 0.085 u) "MUT" "REPORT_LEGEND")
      (setq y (- y (* 0.27 u)))
      (foreach txt SL_SECTION_LEGEND_LINES
        (if (/= txt "") (progn (SL_PaperTextLeft x y (* 0.082 u) txt "REPORT_LEGEND") (setq y (- y (* 0.145 u)))))
      )
    )
  )
)

(defun SL_PaperArrow (x1 y1 x2 y2 size layer / dx dy len ux uy px py)
  (setq dx (- x2 x1) dy (- y2 y1) len (sqrt (+ (* dx dx) (* dy dy))))
  (if (> len 0.000001)
    (progn
      (setq ux (/ dx len) uy (/ dy len) px (- uy) py ux)
      (SL_PaperLine x1 y1 x2 y2 layer)
      (SL_PaperLine x2 y2 (- x2 (* size ux) (* 0.55 size px)) (- y2 (* size uy) (* 0.55 size py)) layer)
      (SL_PaperLine x2 y2 (+ (- x2 (* size ux)) (* 0.55 size px)) (+ (- y2 (* size uy)) (* 0.55 size py)) layer)
    )
  )
)

(defun SL_PaperSectionRulers (vpLeft vpBottom vpW vpH startPos actualLen / spacing sc tick numH labelH textMult xNumOffset yNumOffset labelOffset arrowOffset pos px py rulerX rulerY mid arrowLen)
  (setq spacing SL_RULER_SPACING)
  (setq sc (/ vpH SL_VESSEL_XLEN))
  (setq textMult SL_REPORT_RULER_TEXT_SCALE)
  (setq tick (* 3.0 sc) numH (* 1.8 sc textMult) labelH (* 2.5 sc textMult))
  (setq xNumOffset (+ 5.0 (* 5.0 (max 0.0 (- textMult 1.0)))))
  (setq yNumOffset (+ 5.5 (* 2.0 (max 0.0 (- textMult 1.0)))))
  (setq labelOffset (+ 10.0 (* 8.0 (max 0.0 (- textMult 1.0)))))
  (setq arrowOffset (+ labelOffset 5.5))
  ;; Match the original red X-axis ruler outside the left viewport edge.
  (setq rulerX (- vpLeft (* SL_RULER_OFFSET sc)))
  (SL_PaperLine rulerX vpBottom rulerX (+ vpBottom vpH) "REPORT_X_RULER")
  (setq pos 0.0)
  (while (<= pos SL_VESSEL_XLEN)
    (if (= SL_ORIENTATION "Horizontal CCW")
      (setq py (+ vpBottom (* pos sc)))
      (setq py (- (+ vpBottom vpH) (* pos sc)))
    )
    (SL_PaperLine rulerX py (- rulerX tick) py "REPORT_X_RULER")
    (SL_PaperText (- rulerX (* xNumOffset sc)) py numH 0 (SL_InchLabel pos) "REPORT_X_RULER")
    (setq pos (+ pos spacing))
  )
  (if (> (- SL_VESSEL_XLEN (- pos spacing)) 0.001)
    (progn
      (setq py (if (= SL_ORIENTATION "Horizontal CCW") (+ vpBottom vpH) vpBottom))
      (SL_PaperLine rulerX py (- rulerX tick) py "REPORT_X_RULER")
      (SL_PaperText (- rulerX (* xNumOffset sc)) py numH 0 (SL_InchLabel SL_VESSEL_XLEN) "REPORT_X_RULER")
    )
  )
  (setq mid (+ vpBottom (/ vpH 2.0)))
  (SL_PaperText (- rulerX (* labelOffset sc)) mid labelH 90 SL_X_AXIS_LABEL "REPORT_X_RULER")
  (setq arrowLen (min (* 0.70 vpH) (* (SL_LabelArrowLength SL_X_AXIS_LABEL 2.5 0.0) sc)))
  (if (= SL_ORIENTATION "Horizontal CCW")
    (SL_PaperArrow (- rulerX (* arrowOffset sc)) (- mid (/ arrowLen 2.0))
                   (- rulerX (* arrowOffset sc)) (+ mid (/ arrowLen 2.0))
                   (* SL_ARROW_HEAD sc) "REPORT_X_RULER")
    (SL_PaperArrow (- rulerX (* arrowOffset sc)) (+ mid (/ arrowLen 2.0))
                   (- rulerX (* arrowOffset sc)) (- mid (/ arrowLen 2.0))
                   (* SL_ARROW_HEAD sc) "REPORT_X_RULER")
  )
  ;; Match the original blue Y-axis ruler below the viewport.
  (setq rulerY (- vpBottom (* SL_RULER_OFFSET sc)))
  (SL_PaperLine vpLeft rulerY (+ vpLeft vpW) rulerY "REPORT_Y_RULER")
  (setq pos startPos)
  (while (<= pos (+ startPos actualLen))
    (if (= SL_ORIENTATION "Horizontal CCW")
      (setq px (- (+ vpLeft vpW) (* (- pos startPos) sc)))
      (setq px (+ vpLeft (* (- pos startPos) sc)))
    )
    (SL_PaperLine px rulerY px (- rulerY tick) "REPORT_Y_RULER")
    (SL_PaperText px (- rulerY (* yNumOffset sc)) numH 0 (SL_InchLabel pos) "REPORT_Y_RULER")
    (setq pos (+ pos spacing))
  )
  (if (> (- (+ startPos actualLen) (- pos spacing)) 0.001)
    (progn
      (setq px (if (= SL_ORIENTATION "Horizontal CCW") vpLeft (+ vpLeft vpW)))
      (SL_PaperLine px rulerY px (- rulerY tick) "REPORT_Y_RULER")
      (SL_PaperText px (- rulerY (* yNumOffset sc)) numH 0
                    (SL_InchLabel (+ startPos actualLen)) "REPORT_Y_RULER")
    )
  )
  (setq mid (+ vpLeft (/ vpW 2.0)))
  (SL_PaperText mid (- rulerY (* (+ labelOffset 1.0) sc)) labelH 0 SL_Y_AXIS_LABEL "REPORT_Y_RULER")
  (setq arrowLen (min (* 0.70 vpW) (* (SL_LabelArrowLength SL_Y_AXIS_LABEL 2.5 0.0) sc)))
  (if (= SL_ORIENTATION "Horizontal CCW")
    (SL_PaperArrow (+ mid (/ arrowLen 2.0)) (- rulerY (* (+ arrowOffset 1.0) sc))
                   (- mid (/ arrowLen 2.0)) (- rulerY (* (+ arrowOffset 1.0) sc))
                   (* SL_ARROW_HEAD sc) "REPORT_Y_RULER")
    (SL_PaperArrow (- mid (/ arrowLen 2.0)) (- rulerY (* (+ arrowOffset 1.0) sc))
                   (+ mid (/ arrowLen 2.0)) (- rulerY (* (+ arrowOffset 1.0) sc))
                   (* SL_ARROW_HEAD sc) "REPORT_Y_RULER")
  )
)

(defun c:SECTIONVIEWPORTS ( / *error* oldOsmode pick oldVp ed ctr oldW oldH sectionLen rulerTextScale gap n i startPos endPos actualLen
                              left bottom areaW areaH leftMargin bottomMargin usableW usableH scale
                              vpW vpH vpLeft vpBottom groupBottom totalUsed ll ur vp win1 win2 oldCmdecho)
  (setq oldOsmode (getvar "OSMODE") oldCmdecho (getvar "CMDECHO"))
  (defun *error* (msg)
    (setvar "OSMODE" oldOsmode)
    (setvar "CMDECHO" oldCmdecho)
    (if (and msg (/= msg "Function cancelled") (/= msg "quit / exit abort")) (princ (strcat "\nSECTIONVIEWPORTS error: " msg)))
    (princ)
  )
  (cond
    ((or (null SL_VESSEL_XLEN) (null SL_VESSEL_YLEN))
      (princ "\nRun SCANLAYOUT before creating report viewports."))
    ((/= (getvar "TILEMODE") 0)
      (princ "\nSwitch to the report Sheet tab, then run SECTIONVIEWPORTS again."))
    ((= SL_ORIENTATION "Vertical")
      (princ "\nThis paper-ruler prototype is for Horizontal CW/CCW layouts."))
    (T
      (setq pick (entsel "\nSelect the existing sheet viewport to replace: "))
      (if pick
        (progn
          (setq oldVp (car pick) ed (entget oldVp))
          (if (/= (cdr (assoc 0 ed)) "VIEWPORT")
            (princ "\nThat object is not a sheet viewport.")
            (progn
              (initget 6)
              (setq sectionLen (getreal "\nSection length in inches <360>: "))
              (if (null sectionLen) (setq sectionLen 360.0))
              (initget 6)
              (setq rulerTextScale (getreal "\nRuler text size multiplier <2.0>: "))
              (if (null rulerTextScale) (setq rulerTextScale 2.0))
              (setq SL_REPORT_RULER_TEXT_SCALE rulerTextScale)
              (setq ctr (cdr (assoc 10 ed)) oldW (cdr (assoc 40 ed)) oldH (cdr (assoc 41 ed)))
              (setq left (- (car ctr) (/ oldW 2.0)) bottom (- (cadr ctr) (/ oldH 2.0)))
              (setq areaW oldW areaH oldH gap 0.15 leftMargin 0.65 bottomMargin 0.45)
              (setq n (fix (/ (+ SL_VESSEL_YLEN (- sectionLen 0.0000001)) sectionLen)))
              (setq usableW (- areaW leftMargin))
              (setq usableH (- areaH (* n bottomMargin) (* (1- n) gap)))
              (setq scale (min (/ usableW sectionLen) (/ usableH (* n SL_VESSEL_XLEN))))
              (setq vpH (* SL_VESSEL_XLEN scale))
              (setq totalUsed (+ (* n (+ vpH bottomMargin)) (* (1- n) gap)))
              (setq groupBottom (+ bottom (/ (- areaH totalUsed) 2.0)))
              ;; Paper-space construction must ignore running object snaps.
              (setvar "OSMODE" 0)
              (setvar "CMDECHO" 0)
              (command "_.UNDO" "_Begin")
              (SL_ReturnPaperSpace)
              (SL_UnlockViewport oldVp)
              (command "ERASE" oldVp "")
              (SL_Layer "REPORT_X_RULER" 1)
              (SL_Layer "REPORT_Y_RULER" 5)
              (SL_Layer "REPORT_VIEWPORT" 7)
              (SL_SetLayerPlottable "REPORT_VIEWPORT" T)
              (setq i 0)
              (repeat n
                (setq startPos (* i sectionLen))
                (setq endPos (min SL_VESSEL_YLEN (+ startPos sectionLen)))
                (setq actualLen (- endPos startPos))
                (setq vpW (* actualLen scale))
                (setq vpLeft (+ left leftMargin (/ (- usableW vpW) 2.0)))
                (setq vpBottom (+ groupBottom (* (- n 1 i) (+ vpH bottomMargin gap)) bottomMargin))
                (setq ll (list vpLeft vpBottom) ur (list (+ vpLeft vpW) (+ vpBottom vpH)))
                (SL_SetLayer "REPORT_VIEWPORT")
                (SL_CreateViewport ll ur)
                (setq vp (entlast))
                (if (= SL_ORIENTATION "Horizontal CCW")
                  (progn
                    (setq win1 (list (- endPos) 0.0))
                    (setq win2 (list (- startPos) SL_VESSEL_XLEN))
                  )
                  (progn
                    (setq win1 (list startPos (- SL_VESSEL_XLEN)))
                    (setq win2 (list endPos 0.0))
                  )
                )
                (SL_ActivateViewport vp)
                (command "ZOOM" "W" win1 win2)
                (SL_ReturnPaperSpace)
                (SL_LockViewport vp)
                (SL_PaperSectionRulers vpLeft vpBottom vpW vpH startPos actualLen)
                (setq i (1+ i))
              )
              (command "_.UNDO" "_End")
              (setvar "CMDECHO" oldCmdecho)
              (command "_.REGEN")
              (princ (strcat "\nCreated " (itoa n) " exact-size viewport(s) with paper-space rulers."))
            )
          )
        )
        (princ "\nSECTIONVIEWPORTS cancelled.")
      )
    )
  )
  (setvar "OSMODE" oldOsmode)
  (setvar "CMDECHO" oldCmdecho)
  (princ)
)

;; ------------------------------------------------------------
;; SECTIONPAGES - copy the active letter-size Sheet once per section.
;; The selected viewport defines the usable report rectangle and the active
;; Sheet supplies the existing printer, paper, orientation, border, and title block.
;; ------------------------------------------------------------
(defun SL_ClearSectionSheet (sheetName / ss kill i ent ed layerName)
  (SL_ReturnPaperSpace)
  (setq ss (ssget "_X" (list (cons 0 "VIEWPORT") (cons 410 sheetName))))
  (setq kill (ssadd))
  (if ss
    (progn
      (setq i 0)
      (repeat (sslength ss)
        (setq ent (ssname ss i) ed (entget ent) i (1+ i))
        (if (> (cdr (assoc 69 ed)) 1)
          (progn (SL_UnlockViewport ent) (ssadd ent kill))
        )
      )
    )
  )
  (if (> (sslength kill) 0) (command "ERASE" kill ""))
  (foreach layerName (list "REPORT_X_RULER" "REPORT_Y_RULER" "REPORT_X_REFERENCE" "REPORT_TITLE" "REPORT_LEGEND" "REPORT_LEGEND_AUT" "REPORT_LEGEND_MUT" "REPORT_LEGEND_AUT_BOX" "REPORT_LEGEND_MUT_BOX" "REPORT_VIEWPORT")
    (setq ss (ssget "_X" (list (cons 8 layerName) (cons 410 sheetName))))
    (if ss (command "ERASE" ss ""))
  )
)

(defun SL_SectionPagesStop (msg /)
  ;; Show the reason in a pop-up so the AXISBUILDER menu redraw cannot bury it.
  (princ (strcat "\nSECTIONPAGES: " msg))
  (alert (strcat "SECTIONPAGES cannot run:\n\n" msg))
  (princ)
)

(defun c:SECTIONPAGES ( / *error* oldOsmode pick templateVp ed ctr areaW areaH left bottom templateName
                           sectionLen rulerTextScale n i startPos endPos actualLen
                           leftMargin bottomMargin usableW usableH scale vpW vpH vpLeft vpBottom
                           sheetName firstSheet ll ur vp win1 win2 oldCmdecho infoX infoTop paperUnit)
  (setq oldOsmode (getvar "OSMODE") oldCmdecho (getvar "CMDECHO"))
  (defun *error* (msg)
    (setvar "OSMODE" oldOsmode)
    (setvar "CMDECHO" oldCmdecho)
    (if (and msg (/= msg "Function cancelled") (/= msg "quit / exit abort")) (princ (strcat "\nSECTIONPAGES error: " msg)))
    (princ)
  )
  (cond
    ((or (null SL_VESSEL_XLEN) (null SL_VESSEL_YLEN))
      (SL_SectionPagesStop "Generate the drawing first (SCANLAYOUT, or option 1 / AXISDRAWING in the AXISBUILDER menu), then run SECTIONPAGES again."))
    ((/= (getvar "TILEMODE") 0)
      (SL_SectionPagesStop "Switch to the letter-size template Sheet tab (paper space), then run SECTIONPAGES again."))
    ((= SL_ORIENTATION "Vertical")
      (SL_SectionPagesStop "Section sheets are not available for Vertical orientation yet. Set Project Settings orientation to Horizontal CW or Horizontal CCW, regenerate, and try again."))
    (T
      (setq pick (entsel "\nSelect the template viewport that defines the printable report area: "))
      (if pick
        (progn
          (setq templateVp (car pick) ed (entget templateVp))
          (if (/= (cdr (assoc 0 ed)) "VIEWPORT")
            (princ "\nThat object is not a sheet viewport.")
            (progn
              (initget 6)
              (setq sectionLen (getreal "\nSection length in inches <180>: "))
              (if (null sectionLen) (setq sectionLen 180.0))
              (initget 6)
              (setq rulerTextScale (getreal "\nRuler text size multiplier <2.0>: "))
              (if (null rulerTextScale) (setq rulerTextScale 2.0))
              (setq SL_REPORT_RULER_TEXT_SCALE rulerTextScale)
              (setq ctr (cdr (assoc 10 ed)) areaW (cdr (assoc 40 ed)) areaH (cdr (assoc 41 ed)))
              (setq left (- (car ctr) (/ areaW 2.0)) bottom (- (cadr ctr) (/ areaH 2.0)))
              (setq templateName (getvar "CTAB"))
              ;; Give the section 68% of the sheet while preserving the right information panel.
              (setq leftMargin (* areaW 0.13) bottomMargin (* areaH 0.08) paperUnit (/ areaH 7.5))
              (setq usableW (* areaW 0.68) usableH (- areaH bottomMargin))
              (setq scale (min (/ usableW sectionLen) (/ usableH SL_VESSEL_XLEN)))
              (setq vpH (* SL_VESSEL_XLEN scale))
              (setq n (fix (/ (+ SL_VESSEL_YLEN (- sectionLen 0.0000001)) sectionLen)))
              ;; Paper-space construction must ignore running object snaps.
              (setvar "OSMODE" 0)
              (setvar "CMDECHO" 0)
              (SL_Layer "REPORT_X_RULER" 1)
              (SL_Layer "REPORT_Y_RULER" 5)
              (SL_Layer "REPORT_X_REFERENCE" 1)
              (SL_Layer "REPORT_TITLE" 7)
              (SL_Layer "REPORT_LEGEND" 7)
              (SL_Layer "REPORT_LEGEND_AUT" 5)
              (SL_Layer "REPORT_LEGEND_MUT" 3)
              (SL_Layer "REPORT_LEGEND_AUT_BOX" 5)
              (SL_Layer "REPORT_LEGEND_MUT_BOX" 3)
              (SL_SetLayerTransparency "REPORT_LEGEND_AUT,REPORT_LEGEND_MUT")
              (SL_Layer "REPORT_VIEWPORT" 7)
              (SL_SetLayerPlottable "REPORT_VIEWPORT" T)
              (setq i 0 firstSheet nil)
              (repeat n
                (setq startPos (* i sectionLen))
                (setq endPos (min SL_VESSEL_YLEN (+ startPos sectionLen)))
                (setq actualLen (- endPos startPos))
                (setq sheetName (strcat SL_SECTION_PREFIX (if (< i 9) "0" "") (itoa (1+ i)) "_" (rtos startPos 2 0) "-" (rtos endPos 2 0)))
                (SL_CopySheet templateName sheetName)
                (SL_ActivateSheet sheetName)
                (if (null firstSheet) (setq firstSheet sheetName))
                (SL_ClearSectionSheet sheetName)
                (setq vpW (* actualLen scale))
                (setq vpLeft (+ left leftMargin (/ (- usableW vpW) 2.0)))
                (setq vpBottom (+ bottom bottomMargin (/ (- usableH vpH) 2.0)))
                (setq ll (list vpLeft vpBottom) ur (list (+ vpLeft vpW) (+ vpBottom vpH)))
                (SL_SetLayer "REPORT_VIEWPORT")
                (SL_CreateViewport ll ur)
                (setq vp (entlast))
                (if (= SL_ORIENTATION "Horizontal CCW")
                  (progn (setq win1 (list (- endPos) 0.0)) (setq win2 (list (- startPos) SL_VESSEL_XLEN)))
                  (progn (setq win1 (list startPos (- SL_VESSEL_XLEN))) (setq win2 (list endPos 0.0)))
                )
                (SL_ActivateViewport vp)
                (command "ZOOM" "W" win1 win2)
                (SL_ReturnPaperSpace)
                (SL_LockViewport vp)
                (SL_PaperSectionRulers vpLeft vpBottom vpW vpH startPos actualLen)
                (SL_PaperSectionReferences vpLeft vpBottom vpW vpH)
                ;; Keep the panel clear of the right-side reference labels and
                ;; align the bottom of its legend summary with the section bottom.
                (setq infoX (+ left (* areaW 0.865)) infoTop (+ vpBottom (* 2.55 paperUnit)))
                (SL_PaperSectionInfo infoX infoTop paperUnit)
                (setq i (1+ i))
              )
              (if firstSheet (SL_ActivateSheet firstSheet))
              (setvar "CMDECHO" oldCmdecho)
              (command "_.REGEN")
              (princ (strcat "\nCreated " (itoa n) " letter-size section Sheet tab(s)."))
            )
          )
        )
        (princ "\nSECTIONPAGES cancelled.")
      )
    )
  )
  (setvar "OSMODE" oldOsmode)
  (setvar "CMDECHO" oldCmdecho)
  (princ)
)

;; ------------------------------------------------------------
;; AXISBUILDER - master launcher for AxisBuilder commands.
;; ------------------------------------------------------------
(defun SL_ScanMenuDisplay ()
  (princ "\n========================================")
  (princ "\n              AXISBUILDER")
  (princ "\n========================================")
  (princ "\n  1  Generate Scan Layout")
  (princ "\n  2  Resize Generated Text")
  (princ "\n  3  Wrap Shell Nozzle")
  (princ "\n  4  Wrap Support/Object")
  (princ "\n  5  Create Letter-Size Section Sheets")
  (princ "\n  0  Exit")
)

(defun SL_RunMenuCommand (fn label / result)
  ;; Trap command cancellation/errors so control returns to AXISBUILDER.
  (setq result (vl-catch-all-apply fn nil))
  (if (vl-catch-all-error-p result)
    (princ (strcat "\n" label " stopped: " (vl-catch-all-error-message result)))
  )
  (princ)
)

(defun c:AXISBUILDER ( / choice done)
  (setq done nil)
  (while (not done)
    (SL_ScanMenuDisplay)
    (initget 4)
    (setq choice (getint "\nSelect an option [0-5] <0>: "))
    (if (null choice) (setq choice 0))
    (cond
      ((= choice 0) (setq done T))
      ((= choice 1) (SL_RunMenuCommand 'c:SCANLAYOUT "SCANLAYOUT"))
      ((= choice 2) (SL_RunMenuCommand 'c:TEXTRESIZE "TEXTRESIZE"))
      ((= choice 3) (SL_RunMenuCommand 'c:NOZZLEWRAP "NOZZLEWRAP"))
      ((= choice 4) (SL_RunMenuCommand 'c:OBJECTWRAP "OBJECTWRAP"))
      ((= choice 5) (SL_RunMenuCommand 'c:SECTIONPAGES "SECTIONPAGES"))
      (T (princ "\nInvalid option. Enter 0, 1, 2, 3, 4, or 5."))
    )
  )
  (princ "\nAXISBUILDER closed.")
  (princ)
)

;; Backward-compatible alias for existing workflows.
(defun c:SCANMENU () (c:AXISBUILDER))

(defun SL_HatchRect (x y w h layer / k x1 y1 x2 y2 step)
  ;; Custom 45-degree line hatch. More reliable than interactive HATCH in scripts.
  (setq step SL_HATCH_SPACING)
  (if (<= step 0.0) (setq step 2.5))
  (setq k (- h))
  (while (<= k w)
    (setq x1 (max 0.0 k))
    (setq y1 (- x1 k))
    (setq x2 (min w (+ h k)))
    (setq y2 (- x2 k))
    (if (> x2 x1)
      (SL_Line (+ x x1) (+ y y1) (+ x x2) (+ y y2) layer)
    )
    (setq k (+ k step))
  )
)

(defun SL_FitTextHeight (w h txt / longSide shortSide byShort byLong th)
  ;; Smart text sizing: conservative sizing so labels stay inside scan boxes.
  (setq longSide (max w h))
  (setq shortSide (min w h))
  ;; Limit by short side first, then reduce more for longer labels.
  (setq byShort (* shortSide 0.22))
  (setq byLong (/ (* longSide 0.78) (* (max 1 (strlen txt)) 0.85)))
  (setq th (min byShort byLong))
  (if (< th 0.45) (setq th 0.45))
  th
)

(defun SL_LabelRect (x y w h txt outlineLayer hatchLayer / cx cy rot th)
  (setq cx (+ x (/ w 2.0)))
  (setq cy (+ y (/ h 2.0)))
  (setq rot (if (> h w) 90 0))
  (setq th (SL_FitTextHeight w h txt))
  (SL_Rect x y w h outlineLayer)
  (if (and (/= hatchLayer "") (= SL_HATCH_ENABLED "YES"))
    (SL_HatchRect x y w h hatchLayer)
  )
  (SL_Text cx cy th rot txt outlineLayer)
)

(defun SL_MUTPoint (x y txt / lr)
  ;; Shell manual UT location: MUT ID text only at the recorded X/Y point.
  (setq lr (SL_ReadableRot))
  (SL_Text x y 1.5 lr txt "SHELL_MUT_TEXT")
)

(defun SL_AddAvoidRect (x y w h)
  (setq SL_AVOID_RECTS (cons (list x y (+ x w) (+ y h)) SL_AVOID_RECTS))
)

(defun SL_BBox (cx cy tw th rot / hw hh)
  ;; Approximate text bounding box in logical drawing coordinates.
  (if (= (abs rot) 90)
    (progn (setq hw (/ th 2.0)) (setq hh (/ tw 2.0)))
    (progn (setq hw (/ tw 2.0)) (setq hh (/ th 2.0)))
  )
  (list (- cx hw) (- cy hh) (+ cx hw) (+ cy hh))
)

(defun SL_Overlap (a b)
  (not (or (<= (nth 2 a) (nth 0 b)) (>= (nth 0 a) (nth 2 b)) (<= (nth 3 a) (nth 1 b)) (>= (nth 1 a) (nth 3 b))))
)

(defun SL_ClearBBox (bb / ok r)
  ;; Keep label inside vessel and outside registered objects.
  (setq ok T)
  (if (or (< (nth 0 bb) 0.0) (< (nth 1 bb) 0.0) (> (nth 2 bb) SL_VESSEL_XLEN) (> (nth 3 bb) SL_VESSEL_YLEN)) (setq ok nil))
  (foreach r SL_AVOID_RECTS (if (SL_Overlap bb r) (setq ok nil)))
  ok
)

(defun SL_CircleSmart (x y dia txt mode layer / r th lr tw insideOK outsideNeeded candidates cand lx ly bb found leaderStartX leaderStartY)
  (setq r (/ dia 2.0))
  (setq mode (strcase mode))
  (if (= mode "") (setq mode "AUTO"))
  (SL_SetLayer layer)
  (command "CIRCLE" (SL_pt (SL_tf_x x y) (SL_tf_y x y)) (rtos r 2 3))
  (setq lr (SL_ReadableRot))
  (setq th (max 1.6 (min 2.4 (* dia 0.22))))
  (setq tw (* (max 1 (strlen txt)) th 0.60))
  (setq insideOK (and (>= dia SL_MIN_NOZZLE_DIA) (< tw (* dia 0.75))))
  (setq outsideNeeded (or (= mode "OUTSIDE") (and (= mode "AUTO") (not insideOK)) (= SL_SMART_NOZZLES "NO")))
  (if (= mode "INSIDE") (setq outsideNeeded nil))
  (if (and (/= txt "") (not outsideNeeded))
    (SL_Text x y th lr txt layer)
    (if (/= txt "")
      (progn
        ;; Try positions: right, upper-right, lower-right, left, upper-left, lower-left, above, below.
        (setq candidates (list
          (list (+ x r SL_NOZZLE_LEADER_LEN (/ tw 2.0)) y (+ x r) y)
          (list (+ x r SL_NOZZLE_LEADER_LEN (/ tw 2.0)) (+ y r SL_NOZZLE_LEADER_LEN) (+ x r) (+ y r))
          (list (+ x r SL_NOZZLE_LEADER_LEN (/ tw 2.0)) (- y r SL_NOZZLE_LEADER_LEN) (+ x r) (- y r))
          (list (- x r SL_NOZZLE_LEADER_LEN (/ tw 2.0)) y (- x r) y)
          (list (- x r SL_NOZZLE_LEADER_LEN (/ tw 2.0)) (+ y r SL_NOZZLE_LEADER_LEN) (- x r) (+ y r))
          (list (- x r SL_NOZZLE_LEADER_LEN (/ tw 2.0)) (- y r SL_NOZZLE_LEADER_LEN) (- x r) (- y r))
          (list x (+ y r SL_NOZZLE_LEADER_LEN (/ tw 2.0)) x (+ y r))
          (list x (- y r SL_NOZZLE_LEADER_LEN (/ tw 2.0)) x (- y r))
        ))
        (setq found nil)
        (foreach cand candidates
          (if (not found)
            (progn
              (setq lx (nth 0 cand))
              (setq ly (nth 1 cand))
              (setq bb (SL_BBox lx ly tw th lr))
              (if (SL_ClearBBox bb) (setq found cand))
            )
          )
        )
        (if (not found) (setq found (car candidates)))
        (setq lx (nth 0 found))
        (setq ly (nth 1 found))
        (setq leaderStartX (nth 2 found))
        (setq leaderStartY (nth 3 found))
        (SL_Line leaderStartX leaderStartY lx ly layer)
        (SL_Text lx ly th lr txt layer)
        (setq bb (SL_BBox lx ly tw th lr))
        (SL_AddAvoidRect (nth 0 bb) (nth 1 bb) (- (nth 2 bb) (nth 0 bb)) (- (nth 3 bb) (nth 1 bb)))
      )
    )
  )
  ;; Register nozzle body after placing its label so the current circle does not block its own leader label.
  (SL_AddAvoidRect (- x r) (- y r) dia dia)
)

(defun SL_Arrow (x1 y1 x2 y2 layer / dx dy len ux uy px py ah)
  ;; Draw line plus simple arrowhead.
  (setq ah SL_ARROW_HEAD)
  (setq dx (- x2 x1))
  (setq dy (- y2 y1))
  (setq len (sqrt (+ (* dx dx) (* dy dy))))
  (if (> len 0.0001)
    (progn
      (setq ux (/ dx len))
      (setq uy (/ dy len))
      (setq px (- uy))
      (setq py ux)
      (SL_Line x1 y1 x2 y2 layer)
      (SL_Line x2 y2 (- x2 (* ah ux) (* 0.55 ah px)) (- y2 (* ah uy) (* 0.55 ah py)) layer)
      (SL_Line x2 y2 (+ (- x2 (* ah ux)) (* 0.55 ah px)) (+ (- y2 (* ah uy)) (* 0.55 ah py)) layer)
    )
  )
)

(defun SL_InchLabel (val)
  (strcat (rtos val 2 0) (chr 34))
)

(defun SL_ReadableRot ()
  (cond
    ((= SL_ORIENTATION "Vertical") 0)
    ((= SL_ORIENTATION "Horizontal CW") 90)
    ((= SL_ORIENTATION "Horizontal CCW") -90)
    (T 0)
  )
)

(defun SL_RulerTextRotX ()
  ;; Keeps X-axis ruler inch numbers and direction label readable after orientation transform.
  (cond
    ((= SL_ORIENTATION "Vertical") 0)
    ((= SL_ORIENTATION "Horizontal CW") 180)
    ((= SL_ORIENTATION "Horizontal CCW") 0)
    (T 0)
  )
)

(defun SL_RulerTextRotY ()
  ;; Keeps Y-axis ruler inch numbers and direction label readable after orientation transform.
  (cond
    ((= SL_ORIENTATION "Vertical") 90)
    ((= SL_ORIENTATION "Horizontal CW") 90)
    ((= SL_ORIENTATION "Horizontal CCW") -90)
    (T 90)
  )
)

(defun SL_LabelArrowLength (txt h fixedLen / calc)
  ;; Keep arrow about the length of the direction wording.
  (setq calc (* (strlen txt) h 0.60))
  (if (< calc 14.0) (setq calc 14.0))
  calc
)

(defun SL_RulerX (x0 y0 length spacing layer label / pos tick arrLen mid last)
  (setq pos 0.0)
  (setq last -999.0)
  (setq tick 3.0)
  (SL_Line x0 y0 (+ x0 length) y0 layer)
  (while (<= pos length)
    (SL_Line (+ x0 pos) y0 (+ x0 pos) (- y0 tick) layer)
    (SL_Text (+ x0 pos) (- y0 5.0) 1.8 (SL_RulerTextRotX) (SL_InchLabel pos) layer)
    (setq last pos)
    (setq pos (+ pos spacing))
  )
  ;; Add final dimension tick if length does not land on the selected spacing.
  (if (> (- length last) 0.001)
    (progn
      (SL_Line (+ x0 length) y0 (+ x0 length) (- y0 tick) layer)
      (SL_Text (+ x0 length) (- y0 5.0) 1.8 (SL_RulerTextRotX) (SL_InchLabel length) layer)
    )
  )
  (setq arrLen (SL_LabelArrowLength label 2.5 0.0))
  (setq mid (/ length 2.0))
  (SL_Text (+ x0 mid) (- y0 10.0) 2.5 (SL_RulerTextRotX) label layer)
  (SL_Arrow (- (+ x0 mid) (/ arrLen 2.0)) (- y0 15.5) (+ (+ x0 mid) (/ arrLen 2.0)) (- y0 15.5) layer)
)

(defun SL_RulerX_Top (x0 y0 length spacing layer label / pos tick arrLen mid last)
  ;; Visual top X ruler: ticks, inch numbers, label, and arrow stay above/outside the vessel.
  (setq pos 0.0)
  (setq last -999.0)
  (setq tick 3.0)
  (SL_Line x0 y0 (+ x0 length) y0 layer)
  (while (<= pos length)
    (SL_Line (+ x0 pos) y0 (+ x0 pos) (+ y0 tick) layer)
    (SL_Text (+ x0 pos) (+ y0 5.0) 1.8 (SL_RulerTextRotX) (SL_InchLabel pos) layer)
    (setq last pos)
    (setq pos (+ pos spacing))
  )
  (if (> (- length last) 0.001)
    (progn
      (SL_Line (+ x0 length) y0 (+ x0 length) (+ y0 tick) layer)
      (SL_Text (+ x0 length) (+ y0 5.0) 1.8 (SL_RulerTextRotX) (SL_InchLabel length) layer)
    )
  )
  (setq arrLen (SL_LabelArrowLength label 2.5 0.0))
  (setq mid (/ length 2.0))
  (SL_Text (+ x0 mid) (+ y0 10.0) 2.5 (SL_RulerTextRotX) label layer)
  (SL_Arrow (- (+ x0 mid) (/ arrLen 2.0)) (+ y0 15.5) (+ (+ x0 mid) (/ arrLen 2.0)) (+ y0 15.5) layer)
)

(defun SL_RulerY (x0 y0 length spacing layer label / pos tick arrLen mid last)
  (setq pos 0.0)
  (setq last -999.0)
  (setq tick 3.0)
  (SL_Line x0 y0 x0 (+ y0 length) layer)
  (while (<= pos length)
    (SL_Line x0 (+ y0 pos) (- x0 tick) (+ y0 pos) layer)
    (SL_Text (- x0 5.5) (+ y0 pos) 1.8 (SL_RulerTextRotY) (SL_InchLabel pos) layer)
    (setq last pos)
    (setq pos (+ pos spacing))
  )
  ;; Add final dimension tick if length does not land on the selected spacing.
  (if (> (- length last) 0.001)
    (progn
      (SL_Line x0 (+ y0 length) (- x0 tick) (+ y0 length) layer)
      (SL_Text (- x0 5.5) (+ y0 length) 1.8 (SL_RulerTextRotY) (SL_InchLabel length) layer)
    )
  )
  (setq arrLen (SL_LabelArrowLength label 2.5 0.0))
  (setq mid (/ length 2.0))
  (SL_Text (- x0 11.0) (+ y0 mid) 2.5 (SL_RulerTextRotY) label layer)
  (SL_Arrow (- x0 16.5) (- (+ y0 mid) (/ arrLen 2.0)) (- x0 16.5) (+ (+ y0 mid) (/ arrLen 2.0)) layer)
)

(defun SL_RulerY_Right (x0 y0 length spacing layer label / pos tick arrLen mid last)
  ;; Visual right Y ruler: ticks, inch numbers, label, and arrow stay right/outside the vessel.
  (setq pos 0.0)
  (setq last -999.0)
  (setq tick 3.0)
  (SL_Line x0 y0 x0 (+ y0 length) layer)
  (while (<= pos length)
    (SL_Line x0 (+ y0 pos) (+ x0 tick) (+ y0 pos) layer)
    (SL_Text (+ x0 5.5) (+ y0 pos) 1.8 (SL_RulerTextRotY) (SL_InchLabel pos) layer)
    (setq last pos)
    (setq pos (+ pos spacing))
  )
  (if (> (- length last) 0.001)
    (progn
      (SL_Line x0 (+ y0 length) (+ x0 tick) (+ y0 length) layer)
      (SL_Text (+ x0 5.5) (+ y0 length) 1.8 (SL_RulerTextRotY) (SL_InchLabel length) layer)
    )
  )
  (setq arrLen (SL_LabelArrowLength label 2.5 0.0))
  (setq mid (/ length 2.0))
  (SL_Text (+ x0 11.0) (+ y0 mid) 2.5 (SL_RulerTextRotY) label layer)
  (SL_Arrow (+ x0 16.5) (- (+ y0 mid) (/ arrLen 2.0)) (+ x0 16.5) (+ (+ y0 mid) (/ arrLen 2.0)) layer)
)


;; v4.4.3 dedicated Horizontal CW visual ruler functions.
;; These keep Vertical behavior untouched while mirroring CW visual bottom/left rulers correctly.
(defun SL_RulerX_CW_Left (x0 y0 length spacing layer label / pos tick arrLen mid last)
  ;; Logical X ruler becomes the visual left ruler in Horizontal CW.
  ;; Tick marks are flipped toward the vessel; text stays outside and readable.
  (setq pos 0.0)
  (setq last -999.0)
  (setq tick 3.0)
  (SL_Line x0 y0 (+ x0 length) y0 layer)
  (while (<= pos length)
    (SL_Line (+ x0 pos) y0 (+ x0 pos) (- y0 tick) layer)
    (SL_Text (+ x0 pos) (- y0 5.0) 1.8 (SL_RulerTextRotX) (SL_InchLabel pos) layer)
    (setq last pos)
    (setq pos (+ pos spacing))
  )
  (if (> (- length last) 0.001)
    (progn
      (SL_Line (+ x0 length) y0 (+ x0 length) (- y0 tick) layer)
      (SL_Text (+ x0 length) (- y0 5.0) 1.8 (SL_RulerTextRotX) (SL_InchLabel length) layer)
    )
  )
  (setq arrLen (SL_LabelArrowLength label 2.5 0.0))
  (setq mid (/ length 2.0))
  (SL_Text (+ x0 mid) (- y0 10.0) 2.5 (SL_RulerTextRotX) label layer)
  (SL_Arrow (- (+ x0 mid) (/ arrLen 2.0)) (- y0 15.5) (+ (+ x0 mid) (/ arrLen 2.0)) (- y0 15.5) layer)
)

(defun SL_RulerY_CW_Bottom (x0 y0 length spacing layer label / pos tick arrLen mid last)
  ;; Logical Y ruler is placed at vesselXLen + rulerOffset so it becomes the visual bottom ruler in Horizontal CW.
  ;; Ticks point toward vessel; numbers, direction label, and arrow stay below/outside the ruler.
  (setq pos 0.0)
  (setq last -999.0)
  (setq tick 3.0)
  (SL_Line x0 y0 x0 (+ y0 length) layer)
  (while (<= pos length)
    (SL_Line x0 (+ y0 pos) (+ x0 tick) (+ y0 pos) layer)
    (SL_Text (+ x0 5.5) (+ y0 pos) 1.8 (SL_RulerTextRotY) (SL_InchLabel pos) layer)
    (setq last pos)
    (setq pos (+ pos spacing))
  )
  (if (> (- length last) 0.001)
    (progn
      (SL_Line x0 (+ y0 length) (+ x0 tick) (+ y0 length) layer)
      (SL_Text (+ x0 5.5) (+ y0 length) 1.8 (SL_RulerTextRotY) (SL_InchLabel length) layer)
    )
  )
  (setq arrLen (SL_LabelArrowLength label 2.5 0.0))
  (setq mid (/ length 2.0))
  (SL_Text (+ x0 11.0) (+ y0 mid) 2.5 (SL_RulerTextRotY) label layer)
  (SL_Arrow (+ x0 16.5) (- (+ y0 mid) (/ arrLen 2.0)) (+ x0 16.5) (+ (+ y0 mid) (/ arrLen 2.0)) layer)
)

;; v4.4.8 dedicated Horizontal CCW visual ruler functions.
;; CCW mapping: logical X controls visual LEFT/RIGHT; logical Y controls visual TOP/BOTTOM.
(defun SL_RulerX_CCW_Left (x0 y0 length spacing layer label / pos tick arrLen mid last)
  ;; Logical X ruler at y = vesselYLen + offset becomes the visual left ruler in Horizontal CCW.
  ;; Ticks, numbers, label, and arrow stay outside the vessel.
  (setq pos 0.0)
  (setq last -999.0)
  (setq tick 3.0)
  (SL_Line x0 y0 (+ x0 length) y0 layer)
  (while (<= pos length)
    (SL_Line (+ x0 pos) y0 (+ x0 pos) (+ y0 tick) layer)
    (SL_Text (+ x0 pos) (+ y0 5.0) 1.8 (SL_RulerTextRotX) (SL_InchLabel pos) layer)
    (setq last pos)
    (setq pos (+ pos spacing))
  )
  (if (> (- length last) 0.001)
    (progn
      (SL_Line (+ x0 length) y0 (+ x0 length) (+ y0 tick) layer)
      (SL_Text (+ x0 length) (+ y0 5.0) 1.8 (SL_RulerTextRotX) (SL_InchLabel length) layer)
    )
  )
  (setq arrLen (SL_LabelArrowLength label 2.5 0.0))
  (setq mid (/ length 2.0))
  (SL_Text (+ x0 mid) (+ y0 10.0) 2.5 (SL_RulerTextRotX) label layer)
  (SL_Arrow (- (+ x0 mid) (/ arrLen 2.0)) (+ y0 15.5) (+ (+ x0 mid) (/ arrLen 2.0)) (+ y0 15.5) layer)
)

(defun SL_RulerY_CCW_Bottom (x0 y0 length spacing layer label / pos tick arrLen mid last)
  ;; Logical Y ruler at x = -offset becomes the visual bottom ruler in Horizontal CCW.
  ;; Ticks, numbers, label, and arrow stay outside the vessel.
  (setq pos 0.0)
  (setq last -999.0)
  (setq tick 3.0)
  (SL_Line x0 y0 x0 (+ y0 length) layer)
  (while (<= pos length)
    (SL_Line x0 (+ y0 pos) (- x0 tick) (+ y0 pos) layer)
    (SL_Text (- x0 5.5) (+ y0 pos) 1.8 (SL_RulerTextRotY) (SL_InchLabel pos) layer)
    (setq last pos)
    (setq pos (+ pos spacing))
  )
  (if (> (- length last) 0.001)
    (progn
      (SL_Line x0 (+ y0 length) (- x0 tick) (+ y0 length) layer)
      (SL_Text (- x0 5.5) (+ y0 length) 1.8 (SL_RulerTextRotY) (SL_InchLabel length) layer)
    )
  )
  (setq arrLen (SL_LabelArrowLength label 2.5 0.0))
  (setq mid (/ length 2.0))
  (SL_Text (- x0 11.0) (+ y0 mid) 2.5 (SL_RulerTextRotY) label layer)
  (SL_Arrow (- x0 16.5) (- (+ y0 mid) (/ arrLen 2.0)) (- x0 16.5) (+ (+ y0 mid) (/ arrLen 2.0)) layer)
)

(defun SL_RulerY_CCW_Top (x0 y0 length spacing layer label / pos tick arrLen mid last)
  ;; Logical Y ruler at x = vesselXLen + offset becomes the visual top ruler in Horizontal CCW.
  ;; Ticks, numbers, label, and arrow stay outside the vessel.
  (setq pos 0.0)
  (setq last -999.0)
  (setq tick 3.0)
  (SL_Line x0 y0 x0 (+ y0 length) layer)
  (while (<= pos length)
    (SL_Line x0 (+ y0 pos) (+ x0 tick) (+ y0 pos) layer)
    (SL_Text (+ x0 5.5) (+ y0 pos) 1.8 (SL_RulerTextRotY) (SL_InchLabel pos) layer)
    (setq last pos)
    (setq pos (+ pos spacing))
  )
  (if (> (- length last) 0.001)
    (progn
      (SL_Line x0 (+ y0 length) (+ x0 tick) (+ y0 length) layer)
      (SL_Text (+ x0 5.5) (+ y0 length) 1.8 (SL_RulerTextRotY) (SL_InchLabel length) layer)
    )
  )
  (setq arrLen (SL_LabelArrowLength label 2.5 0.0))
  (setq mid (/ length 2.0))
  (SL_Text (+ x0 11.0) (+ y0 mid) 2.5 (SL_RulerTextRotY) label layer)
  (SL_Arrow (+ x0 16.5) (- (+ y0 mid) (/ arrLen 2.0)) (+ x0 16.5) (+ (+ y0 mid) (/ arrLen 2.0)) layer)
)

(defun SL_Legend (x y / boxW boxH lr orient covTxt covLoc totalTxt orientTxt overlayTxt lineStep)
  ;; Compact legend with project summary lines. Orientation is simplified to Horizontal or Vertical for client-facing output.
  (setq boxW 12.0)
  (setq boxH 7.0)
  (setq lineStep 3.1)
  (setq lr (SL_ReadableRot))
  (setq orient (strcase SL_ORIENTATION))
  (setq covTxt SL_COVERAGE_TEXT)
  (setq covLoc (strcase SL_COVERAGE_LOCATION))
  (setq totalTxt SL_LEGEND_TOTAL_SCANS_TEXT)
  (setq orientTxt SL_LEGEND_ORIENTATION_TEXT)
  (setq overlayTxt SL_LEGEND_OVERLAY_TEXT)
  (if (= orient "VERTICAL")
    (progn
      ;; Vertical rollout: AUT and MUT use one visual row and the same visual rectangle shape as horizontal rollouts.
      (SL_Text (+ x 6.0) (+ y 25.0) 2.3 lr "LEGEND" "LEGEND")
      (if (= SL_HATCH_ENABLED "YES")
        (progn
          (SL_Rect x (+ y 8.0) boxH boxW "LEGEND_SAMPLE")
          (SL_HatchRect x (+ y 8.0) boxH boxW "LEGEND_AUT_HATCH")
          (SL_Text (+ x 3.5) (+ y 5.0) 2.0 lr "AUT" "LEGEND")
        )
      )
      (SL_Rect (+ x 8.0) (+ y 8.0) boxH boxW "LEGEND_SAMPLE")
      (SL_HatchRect (+ x 8.0) (+ y 8.0) boxH boxW "LEGEND_MUT_HATCH")
      (SL_Text (+ x 11.5) (+ y 5.0) 2.0 lr "MUT" "LEGEND")
    )
    (progn
      ;; Horizontal rollouts: boxes read side-by-side after the coordinate transform.
      (if (= orient "HORIZONTAL CCW")
        (SL_Text (+ x 19.0) (+ y 9.0) 2.3 lr "LEGEND" "LEGEND")
        (SL_Text (- x 5.0) (+ y 6.0) 2.3 lr "LEGEND" "LEGEND")
      )
      (SL_Rect x y boxW boxH "LEGEND_SAMPLE")
      (SL_HatchRect x y boxW boxH "LEGEND_MUT_HATCH")
      (SL_Text (+ x 15.0) (+ y 3.5) 2.0 lr "MUT" "LEGEND")
      (if (= SL_HATCH_ENABLED "YES")
        (progn
          (SL_Rect x (+ y 8.0) boxW boxH "LEGEND_SAMPLE")
          (SL_HatchRect x (+ y 8.0) boxW boxH "LEGEND_AUT_HATCH")
          (SL_Text (+ x 15.0) (+ y 11.5) 2.0 lr "AUT" "LEGEND")
        )
      )
    )
  )
  ;; Legend summary stack: Total Scans, Coverage, Orientation, Overlay.
  (cond
    ((= orient "VERTICAL")
      (SL_TextLeft x (- y 1.5) 2.0 lr totalTxt "LEGEND")
      (if (and (> (strlen covTxt) 0) (= covLoc "LEGEND")) (SL_TextLeft x (- y 4.6) 2.0 lr covTxt "LEGEND"))
      (SL_TextLeft x (- y 7.7) 2.0 lr orientTxt "LEGEND")
      (SL_TextLeft x (- y 10.8) 2.0 lr overlayTxt "LEGEND")
    )
    ((= orient "HORIZONTAL CW")
      (SL_TextLeft (+ x 21.5) y 2.0 lr totalTxt "LEGEND")
      (if (and (> (strlen covTxt) 0) (= covLoc "LEGEND")) (SL_TextLeft (+ x 24.6) y 2.0 lr covTxt "LEGEND"))
      (SL_TextLeft (+ x 27.7) y 2.0 lr orientTxt "LEGEND")
      (SL_TextLeft (+ x 30.8) y 2.0 lr overlayTxt "LEGEND")
    )
    ((= orient "HORIZONTAL CCW")
      (SL_TextLeft (- x 6.5) (+ y 15.0) 2.0 lr totalTxt "LEGEND")
      (if (and (> (strlen covTxt) 0) (= covLoc "LEGEND")) (SL_TextLeft (- x 9.6) (+ y 15.0) 2.0 lr covTxt "LEGEND"))
      (SL_TextLeft (- x 12.7) (+ y 15.0) 2.0 lr orientTxt "LEGEND")
      (SL_TextLeft (- x 15.8) (+ y 15.0) 2.0 lr overlayTxt "LEGEND")
    )
    (T
      (SL_TextLeft x (- y 1.5) 2.0 lr totalTxt "LEGEND")
      (if (and (> (strlen covTxt) 0) (= covLoc "LEGEND")) (SL_TextLeft x (- y 4.6) 2.0 lr covTxt "LEGEND"))
      (SL_TextLeft x (- y 7.7) 2.0 lr orientTxt "LEGEND")
      (SL_TextLeft x (- y 10.8) 2.0 lr overlayTxt "LEGEND")
    )
  )
)

(defun SL_DashLine (x1 y1 x2 y2 dash gap layer / dx dy len ux uy pos segEnd)
  (setq dx (- x2 x1))
  (setq dy (- y2 y1))
  (setq len (sqrt (+ (* dx dx) (* dy dy))))
  (if (> len 0.0001)
    (progn
      (setq ux (/ dx len))
      (setq uy (/ dy len))
      (setq pos 0.0)
      (while (< pos len)
        (setq segEnd (min len (+ pos dash)))
        (SL_Line (+ x1 (* ux pos)) (+ y1 (* uy pos)) (+ x1 (* ux segEnd)) (+ y1 (* uy segEnd)) layer)
        (setq pos (+ pos dash gap))
      )
    )
  )
)

(defun SL_CircWeld (loc start stop vesselXLen label / x1 x2 mid)
  ;; Circumferential weld: Location is Y position. Line runs in X-axis direction.
  (setq x1 (if (< start 0.0) 0.0 start))
  (setq x2 (if (< stop 0.0) vesselXLen stop))
  (SL_DashLine x1 loc x2 loc 4.0 2.5 "CIRC_WELDS")
  (if (/= label "") (SL_Text (- x2 3.0) loc 2.0 0 label "CIRC_WELDS"))
)

(defun SL_LongSeam (loc start stop vesselYLen label / y1 y2 labelY)
  ;; Long seam: Location is X position. Line runs in Y-axis direction.
  ;; Label is placed inside the vessel near the seam start instead of centered.
  (setq y1 (if (< start 0.0) 0.0 start))
  (setq y2 (if (< stop 0.0) vesselYLen stop))
  (setq labelY (+ y1 6.0))
  (if (> labelY (- y2 2.0)) (setq labelY (+ y1 (/ (- y2 y1) 2.0))))
  (SL_DashLine loc y1 loc y2 4.0 2.5 "LONG_SEAMS")
  (if (/= label "") (SL_Text loc labelY 2.0 90 label "LONG_SEAMS"))
)

(defun SL_Centerline (vesselXLen vesselYLen / cx)
  ;; Long-dash centerline, runs with Y-axis direction at vessel midpoint.
  (setq cx (/ vesselXLen 2.0))
  (SL_DashLine cx 0.0 cx vesselYLen 8.0 5.0 "CENTERLINE")
)

(defun SL_TitleBlock (x y title component unit client inspector dte rev / lr lineH orient lines i tx ty)
  ;; Title block is placed outside the vessel. Line stacking is orientation-aware.
  (setq lr (SL_ReadableRot))
  (setq lineH 3.4)
  (setq orient (strcase SL_ORIENTATION))
  (setq lines (list title component unit client inspector dte rev))
  (setq i 0)
  (foreach txt lines
    (if (/= txt "")
      (progn
        (cond
          ((= orient "HORIZONTAL CW") (setq tx (+ x (* i lineH))) (setq ty y))
          ((= orient "HORIZONTAL CCW") (setq tx (- x (* i lineH))) (setq ty y))
          (T (setq tx x) (setq ty (- y (* i lineH))))
        )
        (SL_TextLeft tx ty (if (= i 0) 2.4 1.8) lr txt "TITLE_BLOCK")
      )
    )
    (setq i (+ i 1))
  )
)
(defun SL_HeadVector (deg / rad sx sy)
  ;; Converts clock-position angle to logical vector based on vessel orientation.
  ;; 0 degrees = 12 o'clock/top; 90 degrees = 3 o'clock/right.
  (setq rad (* deg (/ pi 180.0)))
  (setq sx (sin rad))
  (setq sy (cos rad))
  (cond
    ((= SL_ORIENTATION "Vertical") (list sx sy))
    ((= SL_ORIENTATION "Horizontal CW") (list (- sy) sx))
    ((= SL_ORIENTATION "Horizontal CCW") (list sy (- sx)))
    (T (list (- sy) sx))
  )
)

(defun SL_HeadLabelPoint (cx cy r / orient)
  ;; Returns a point visually above the head for the head title.
  (setq orient (strcase SL_ORIENTATION))
  (cond
    ((= orient "HORIZONTAL CW") (list (- cx r 9.0) cy))
    ((= orient "HORIZONTAL CCW") (list (+ cx r 9.0) cy))
    (T (list cx (+ cy r 9.0)))
  )
)

(defun SL_HeadClockRef (cx cy r / hv dx dy sx sy ex ey tx ty lr)
  ;; Shows a small 12 o'clock reference above the head when enabled.
  (if (= (strcase SL_SHOW_HEAD_CLOCK_REF) "YES")
    (progn
      (setq hv (SL_HeadVector 0.0))
      (setq dx (nth 0 hv))
      (setq dy (nth 1 hv))
      (setq sx (+ cx (* (+ r 2.0) dx)))
      (setq sy (+ cy (* (+ r 2.0) dy)))
      (setq ex (+ cx (* (+ r 7.0) dx)))
      (setq ey (+ cy (* (+ r 7.0) dy)))
      (SL_Arrow sx sy ex ey "HEADS")
      (setq tx (+ cx (* (+ r 10.0) dx)))
      (setq ty (+ cy (* (+ r 10.0) dy)))
      (setq lr (SL_ReadableRot))
      (SL_Text tx ty 1.7 lr "12" "HEAD_CLOCK_TEXT")
    )
  )
)

(defun SL_HeadCrosshairs (cx cy r /)
  ;; Optional light crosshair reference through the head center.
  (if (= (strcase SL_SHOW_HEAD_CENTERLINES) "YES")
    (progn
      (SL_DashLine (- cx r) cy (+ cx r) cy 3.0 2.5 "HEADS")
      (SL_DashLine cx (- cy r) cx (+ cy r) 3.0 2.5 "HEADS")
    )
  )
)

(defun SL_HeadView (cx cy dia label / r lr p)
  ;; Optional head view shown in the right-side panel.
  (setq r (/ dia 2.0))
  (setq lr (SL_ReadableRot))
  (SL_SetLayer "HEADS")
  (command "CIRCLE" (SL_pt (SL_tf_x cx cy) (SL_tf_y cx cy)) (rtos r 2 3))
  (SL_HeadCrosshairs cx cy r)
  (SL_HeadClockRef cx cy r)
  (setq p (SL_HeadLabelPoint cx cy r))
  (SL_Text (nth 0 p) (nth 1 p) 2.3 lr label "HEAD_TITLE_TEXT")
)

(defun SL_HeadNozzle (hcX hcY headDia deg factor dia txt mode layer / hv dx dy r nozR x y th lr insideOK outsideNeeded sx sy ex ey tx ty)
  ;; Head nozzle placement. Clock position controls direction; radius factor controls distance from head center.
  ;; The calculated point is the nozzle centerline penetration point.
  (setq hv (SL_HeadVector deg))
  (setq dx (nth 0 hv))
  (setq dy (nth 1 hv))
  (setq r (/ headDia 2.0))
  (setq nozR (/ dia 2.0))
  (setq x (+ hcX (* r factor dx)))
  (setq y (+ hcY (* r factor dy)))
  (setq lr (SL_ReadableRot))
  (setq th (max 1.4 (min 2.2 (* dia 0.22))))
  (setq mode (strcase mode))
  (if (= mode "") (setq mode "AUTO"))
  (SL_SetLayer layer)
  (command "CIRCLE" (SL_pt (SL_tf_x x y) (SL_tf_y x y)) (rtos nozR 2 3))
  ;; Head labels stay outside more aggressively than shell nozzles to keep head views clean.
  (setq insideOK (and (>= dia (+ SL_MIN_NOZZLE_DIA 2.0)) (< (* (strlen txt) th 0.55) (* dia 0.65))))
  (setq outsideNeeded (or (= mode "OUTSIDE") (and (= mode "AUTO") (not insideOK))))
  (if (= mode "INSIDE") (setq outsideNeeded nil))
  (if (/= txt "")
    (if outsideNeeded
      (progn
        ;; Leader points outward from head center through nozzle location.
        (setq sx (+ x (* nozR dx)))
        (setq sy (+ y (* nozR dy)))
        (setq ex (+ x (* (+ nozR SL_HEAD_NOZZLE_LEADER_LEN 4.0) dx)))
        (setq ey (+ y (* (+ nozR SL_HEAD_NOZZLE_LEADER_LEN 4.0) dy)))
        (setq tx (+ x (* (+ nozR SL_HEAD_NOZZLE_LEADER_LEN 8.0) dx)))
        (setq ty (+ y (* (+ nozR SL_HEAD_NOZZLE_LEADER_LEN 8.0) dy)))
        (SL_Line sx sy ex ey layer)
        (SL_Text tx ty th lr txt "HEAD_NOZZLE_TEXT")
      )
      (SL_Text x y th lr txt "HEAD_NOZZLE_TEXT")
    )
  )
)

(defun SL_HeadMUT (hcX hcY headDia deg factor txt layer / hv dx dy r x y lr)
  ;; Head manual UT location: MUT ID text only at the recorded clock/radius position.
  (setq hv (SL_HeadVector deg))
  (setq dx (nth 0 hv))
  (setq dy (nth 1 hv))
  (setq r (/ headDia 2.0))
  (setq x (+ hcX (* r factor dx)))
  (setq y (+ hcY (* r factor dy)))
  (setq lr (SL_ReadableRot))
  (if (/= txt "") (SL_Text x y 1.5 lr txt "HEAD_MUT_TEXT"))
)


;;; Overlay image insertion helpers
(defun SL_OverlayLL (x y w h / p)
  ;; Lower-left insertion point after coordinate transform.
  (cond
    ((= SL_ORIENTATION "Vertical") (SL_pt (SL_tf_x x y) (SL_tf_y x y)))
    ((= SL_ORIENTATION "Horizontal CW") (SL_pt (SL_tf_x (+ x w) y) (SL_tf_y (+ x w) y)))
    ((= SL_ORIENTATION "Horizontal CCW") (SL_pt (SL_tf_x x (+ y h)) (SL_tf_y x (+ y h))))
    (T (SL_pt (SL_tf_x x y) (SL_tf_y x y)))
  )
)

(defun SL_InsertFitImage (x y w h img / ins sc rot)
  (SL_SetLayer "SCAN_IMAGES")
  ;; v3.0B.20 TEST: CCW overlay insert/rotation added.
  ;; Confirmed working: Vertical = x,y rot 0; Horizontal CW = y,-x rot -90; sc = w.
  ;; CCW test: insertion = -y,x; rot = 90; sc = w.
  (setq sc w)
  (cond
    ((= SL_ORIENTATION "Vertical")
      (setq ins (strcat (rtos x 2 4) "," (rtos y 2 4)))
      (setq rot "0")
    )
    ((= SL_ORIENTATION "Horizontal CCW")
      (setq ins (strcat (rtos (- y) 2 4) "," (rtos x 2 4)))
      (setq rot "90")
    )
    (T
      (setq ins (strcat (rtos y 2 4) "," (rtos (- x) 2 4)))
      (setq rot "-90")
    )
  )
  (command "EDITIMAGE" "Attach" img ins (rtos sc 2 8) rot)
)

(setq SL_ORIENTATION "Horizontal CW")
(setq SL_SECTION_PREFIX "OVL-SEC-")
(setq SL_HATCH_ENABLED "YES")
(setq SL_HATCH_SPACING 2.5)
(setq SL_HATCH_ANGLE 45.)
(setq SL_COVERAGE_TEXT "Coverage: 18.1%")
(setq SL_COVERAGE_LOCATION "LEGEND")
(setq SL_LEGEND_TOTAL_SCANS_TEXT "Total Scans: 17")
(setq SL_LEGEND_ORIENTATION_TEXT "Orientation: Horizontal")
(setq SL_LEGEND_OVERLAY_TEXT "Overlay: Enabled")
(setq SL_OVERLAY_PPI 40.)
(setq SL_OVERLAY_SCALE 10.)
(setq SL_OVERLAY_ROTATION 0.)
(setq SL_ARROW_HEAD 3.)
(setq SL_SMART_NOZZLES "YES")
(setq SL_MIN_NOZZLE_DIA 6.)
(setq SL_NOZZLE_LEADER_LEN 4.)
(setq SL_SHOW_HEAD_CENTERLINES "NO")
(setq SL_SHOW_HEAD_CLOCK_REF "NO")
(setq SL_HEAD_NOZZLE_LEADER_LEN 8.)

(setq SL_RULER_SPACING 20.)
(setq SL_RULER_OFFSET 2.)
(setq SL_X_AXIS_LABEL "X AXIS DIRECTION TDC CLOCK WISE LOOKING EAST")
(setq SL_Y_AXIS_LABEL "Y AXIS DIRECTION WEST TO EAST")
(setq SL_SECTION_SHOW_REFS "YES")
(setq SL_SECTION_REF_LABELS (list "T.D.C." "R.D.C." "B.D.C." "L.D.C." "T.D.C."))
(setq SL_SECTION_SHOW_TITLE "YES")
(setq SL_SECTION_SHOW_LEGEND "YES")
(setq SL_SECTION_TITLE_LINES (list "AUT Corrosion Mapping" "COMPONENT: VESSEL REF1-OFF" "UNIT: UNIT 1" "CLIENT: CLIENT A" "INSPECTOR: INSPECTOR A" "DATE: 10/13/26" "REV: "))
(setq SL_SECTION_LEGEND_LINES (list SL_LEGEND_TOTAL_SCANS_TEXT SL_COVERAGE_TEXT SL_LEGEND_ORIENTATION_TEXT SL_LEGEND_OVERLAY_TEXT))

(defun c:SCANOVERLAY ( / vesselXLen vesselYLen spacing oldOsmode)
  ;; Prevent running object snaps from pulling generated geometry and images onto nearby corners.
  (setq oldOsmode (getvar "OSMODE"))
  (setvar "OSMODE" 0)
  (SL_SetupLayers)
  (SL_SetupViewportLayers)
  (setvar "UCSICON" 0)
  (setvar "IMAGEFRAME" 1)
  (setq vesselXLen 302.)
  (setq vesselYLen 360.)
  (setq spacing 20.)
  (setq SL_VESSEL_XLEN vesselXLen)
  (setq SL_VESSEL_YLEN vesselYLen)
  (setq SL_AVOID_RECTS nil)

  ;; Vessel border
  (SL_Rect 0.0 0.0 vesselXLen vesselYLen "VESSEL")
  (SL_Centerline vesselXLen vesselYLen)

  ;; Layout scan geometry is generated with the images so the drawing only needs to be built once.
  (SL_LabelRect 115. 2. 72. 20. "SCAN 1" "SCANS" "AUT_HATCH")
  (SL_LabelRect 115. 22. 72. 20. "SCAN 2" "SCANS" "AUT_HATCH")
  (SL_LabelRect 115. 57. 31. 20. "SCAN 3" "SCANS" "AUT_HATCH")
  (SL_LabelRect 156. 57. 31. 20. "SCAN 4" "SCANS" "AUT_HATCH")
  (SL_LabelRect 115. 77. 72. 20. "SCAN 5" "SCANS" "AUT_HATCH")
  (SL_LabelRect 115. 97. 72. 20. "SCAN 6" "SCANS" "AUT_HATCH")
  (SL_LabelRect 115. 122. 72. 20. "SCAN 7" "SCANS" "AUT_HATCH")
  (SL_LabelRect 115. 142. 72. 20. "SCAN 8" "SCANS" "AUT_HATCH")
  (SL_LabelRect 115. 162. 72. 20. "SCAN 9" "SCANS" "AUT_HATCH")
  (SL_LabelRect 120. 182. 67. 20. "SCAN 10" "SCANS" "AUT_HATCH")
  (SL_LabelRect 115. 202. 72. 20. "SCAN 11" "SCANS" "AUT_HATCH")
  (SL_LabelRect 115. 222. 72. 15. "SCAN 12" "SCANS" "AUT_HATCH")
  (SL_LabelRect 125. 242. 62. 20. "SCAN 13" "SCANS" "AUT_HATCH")
  (SL_LabelRect 125. 262. 62. 20. "SCAN 14" "SCANS" "AUT_HATCH")
  (SL_LabelRect 128. 282. 15. 19. "SCAN 15" "SCANS" "AUT_HATCH")
  (SL_LabelRect 162. 282. 18. 19. "SCAN 16" "SCANS" "AUT_HATCH")
  (SL_LabelRect 115. 315. 72. 20. "SCAN 17" "SCANS" "AUT_HATCH")

  ;; Scan image overlays. IMAGEFRAME follows Project Settings: Show Scan Borders On Overlay.
  (SL_InsertFitImage 115. 2. 72. 20. "<PROCESSED_IMAGES>/S1_FIT_B12.png")
  (SL_AddAvoidRect 115. 2. 72. 20.)
  (SL_InsertFitImage 115. 22. 72. 20. "<PROCESSED_IMAGES>/S2_FIT_B12.png")
  (SL_AddAvoidRect 115. 22. 72. 20.)
  (SL_InsertFitImage 115. 57. 31. 20. "<PROCESSED_IMAGES>/S3_FIT_B12.png")
  (SL_AddAvoidRect 115. 57. 31. 20.)
  (SL_InsertFitImage 156. 57. 31. 20. "<PROCESSED_IMAGES>/S4_FIT_B12.png")
  (SL_AddAvoidRect 156. 57. 31. 20.)
  (SL_InsertFitImage 115. 77. 72. 20. "<PROCESSED_IMAGES>/S5_FIT_B12.png")
  (SL_AddAvoidRect 115. 77. 72. 20.)
  (SL_InsertFitImage 115. 97. 72. 20. "<PROCESSED_IMAGES>/S6_FIT_B12.png")
  (SL_AddAvoidRect 115. 97. 72. 20.)
  (SL_InsertFitImage 115. 122. 72. 20. "<PROCESSED_IMAGES>/S7_FIT_B12.png")
  (SL_AddAvoidRect 115. 122. 72. 20.)
  (SL_InsertFitImage 115. 142. 72. 20. "<PROCESSED_IMAGES>/S8_FIT_B12.png")
  (SL_AddAvoidRect 115. 142. 72. 20.)
  (SL_InsertFitImage 115. 162. 72. 20. "<PROCESSED_IMAGES>/S9_FIT_B12.png")
  (SL_AddAvoidRect 115. 162. 72. 20.)
  (SL_InsertFitImage 120. 182. 67. 20. "<PROCESSED_IMAGES>/S10_FIT_B12.png")
  (SL_AddAvoidRect 120. 182. 67. 20.)
  (SL_InsertFitImage 115. 202. 72. 20. "<PROCESSED_IMAGES>/S11_FIT_B12.png")
  (SL_AddAvoidRect 115. 202. 72. 20.)
  (SL_InsertFitImage 115. 222. 72. 15. "<PROCESSED_IMAGES>/S12_FIT_B12.png")
  (SL_AddAvoidRect 115. 222. 72. 15.)
  (SL_InsertFitImage 125. 242. 62. 20. "<PROCESSED_IMAGES>/S13_FIT_B12.png")
  (SL_AddAvoidRect 125. 242. 62. 20.)
  (SL_InsertFitImage 125. 262. 62. 20. "<PROCESSED_IMAGES>/S14_FIT_B12.png")
  (SL_AddAvoidRect 125. 262. 62. 20.)
  (SL_InsertFitImage 128. 282. 15. 19. "<PROCESSED_IMAGES>/S15_FIT_B12.png")
  (SL_AddAvoidRect 128. 282. 15. 19.)
  (SL_InsertFitImage 162. 282. 18. 19. "<PROCESSED_IMAGES>/S16_FIT_B12.png")
  (SL_AddAvoidRect 162. 282. 18. 19.)
  (SL_InsertFitImage 115. 315. 72. 20. "<PROCESSED_IMAGES>/S17_FIT_B12.png")
  (SL_AddAvoidRect 115. 315. 72. 20.)

  ;; Supports / structures
  (SL_LabelRect 97. 46. 110. 9. "SUPPORT 1" "SUPPORTS" "")
  (SL_AddAvoidRect 97. 46. 110. 9.)
  (SL_LabelRect 97. 304. 110. 9. "SUPPORT 2" "SUPPORTS" "")
  (SL_AddAvoidRect 97. 304. 110. 9.)
  (SL_LabelRect 45. 71. 9. 12. "NT" "SUPPORTS" "")
  (SL_AddAvoidRect 45. 71. 9. 12.)

  ;; Nozzles
  (SL_CircleSmart 151. 66. 4. "N1" "AUTO" "NOZZLES")
  (SL_CircleSmart 194. 180. 4. "N2" "AUTO" "NOZZLES")
  (SL_CircleSmart 114. 190. 2. "N3" "AUTO" "NOZZLES")
  (SL_CircleSmart 57. 190. 2. "N4" "AUTO" "NOZZLES")
  (SL_CircleSmart 102. 265. 24. "MW" "AUTO" "NOZZLES")
  (SL_CircleSmart 114. 294. 2. "N6" "AUTO" "NOZZLES")
  (SL_CircleSmart 57. 294. 2. "N7" "AUTO" "NOZZLES")
  (SL_CircleSmart 151. 294. 4. "N8" "AUTO" "NOZZLES")
  (SL_CircleSmart 83. 308. 2. "N9" "AUTO" "NOZZLES")
  (SL_CircleSmart 55. 308. 2. "N10" "AUTO" "NOZZLES")
  (SL_CircleSmart 57. 344. 2. "N11" "AUTO" "NOZZLES")
  (SL_CircleSmart 83. 344. 4. "N12" "AUTO" "NOZZLES")
  (SL_CircleSmart 112. 344. 2. "N13" "AUTO" "NOZZLES")
  (SL_CircleSmart 83. 354. 4. "N14" "AUTO" "NOZZLES")
  (SL_CircleSmart 112. 354. 4. "N15" "AUTO" "NOZZLES")
  (SL_CircleSmart 142. 351. 6. "N16" "AUTO" "NOZZLES")
  (SL_CircleSmart 158. 351. 4. "N17" "AUTO" "NOZZLES")
  (SL_CircleSmart 186. 354. 4. "N18" "AUTO" "NOZZLES")
  (SL_CircleSmart 213. 354. 4. "N19" "AUTO" "NOZZLES")
  (SL_CircleSmart 264. 354. 4. "N20" "AUTO" "NOZZLES")

  ;; Shell MUT points - rows 91-110: A=MUT ID, B=X, C=Y, D=Min. T., E=Notes

  ;; Welds
  (SL_CircWeld 120. -1. -1. vesselXLen "C1")
  (SL_CircWeld 240. -1. -1. vesselXLen "C2")

  ;; Optional rulers on overlay
  ;; Horizontal CW visual BOTTOM + LEFT rulers
  (SL_RulerY_CW_Bottom (+ vesselXLen 2.) 0.0 vesselYLen spacing "Y_AXIS" "Y AXIS DIRECTION WEST TO EAST")
  (SL_RulerX_CW_Left 0.0 (- 0.0 2.) vesselXLen spacing "X_AXIS" "X AXIS DIRECTION TDC CLOCK WISE LOOKING EAST")

  ;; Optional vessel reference indicators on overlay
  ;; Vessel reference labels - v4.6.2 cardinal vessel X-axis references
  (SL_Line 0.0 vesselYLen 0.0 (+ vesselYLen 2.) "X_AXIS")
  (SL_Text 0.0 (+ vesselYLen 3.25) 1.5 (SL_RulerTextRotX) "T.D.C." "X_AXIS")
  (SL_Line (* vesselXLen 0.25) vesselYLen (* vesselXLen 0.25) (+ vesselYLen 2.) "X_AXIS")
  (SL_Text (* vesselXLen 0.25) (+ vesselYLen 3.25) 1.5 (SL_RulerTextRotX) "R.D.C." "X_AXIS")
  (SL_Line (/ vesselXLen 2.0) vesselYLen (/ vesselXLen 2.0) (+ vesselYLen 2.) "X_AXIS")
  (SL_Text (/ vesselXLen 2.0) (+ vesselYLen 3.25) 1.5 (SL_RulerTextRotX) "B.D.C." "X_AXIS")
  (SL_Line (* vesselXLen 0.75) vesselYLen (* vesselXLen 0.75) (+ vesselYLen 2.) "X_AXIS")
  (SL_Text (* vesselXLen 0.75) (+ vesselYLen 3.25) 1.5 (SL_RulerTextRotX) "L.D.C." "X_AXIS")
  (SL_Line vesselXLen vesselYLen vesselXLen (+ vesselYLen 2.) "X_AXIS")
  (SL_Text vesselXLen (+ vesselYLen 3.25) 1.5 (SL_RulerTextRotX) "T.D.C." "X_AXIS")

  (SL_Legend 271.2 372.)

  (SL_TitleBlock 227.6 372. "AUT Corrosion Mapping" "COMPONENT: VESSEL REF1-OFF" "UNIT: UNIT 1" "CLIENT: CLIENT A" "INSPECTOR: INSPECTOR A" "DATE: 10/13/26" "REV: ")

  (command "ZOOM" "E")
  (SL_OverlayView)
  ;; DraftSight creates the usable viewport entity when Sheet1 is activated.
  ;; Activate it first, then move it to the dedicated non-print layer.
  (SL_ActivateSheet "Sheet1")
  (SL_AssignCurrentSheetViewports)
  (command "_.REGEN")
  ;; Return to Model space after the Sheet1 viewport has been updated.
  (setvar "TILEMODE" 1)
  (setvar "OSMODE" oldOsmode)
  (princ "\nAxisBuilder master drawing complete. Normal viewport is non-printing; Model space is active.")
  (princ)
)
(defun c:AXISDRAWING () (c:SCANOVERLAY))

;; Layer visibility controls for the one-drawing AxisBuilder workflow.
(defun SL_LayerOn (name) (command "_.-LAYER" "_On" name ""))
(defun SL_LayerOff (name) (command "_.-LAYER" "_Off" name ""))
(defun SL_LayoutView ()
  (SL_SetLayer "0")
  (SL_LayerOff "SCAN_IMAGES")
  (SL_LayerOn "SCANS")
  (SL_LayerOn "SCAN_TEXT")
  (SL_LayerOn "AUT_HATCH")
  (setvar "IMAGEFRAME" 0)
  (command "_.REGEN")
  (princ "\nAxisBuilder Layout View active.")
  (princ)
)
(defun c:ABLAYOUT () (SL_LayoutView))

(defun SL_OverlayView ()
  (SL_SetLayer "0")
  (SL_LayerOn "SCAN_IMAGES")
  (SL_LayerOff "AUT_HATCH")
  (SL_LayerOff "SCAN_TEXT")
  (SL_LayerOff "SCANS")
  (setvar "IMAGEFRAME" 1)
  (command "_.REGEN")
  (princ "\nAxisBuilder Overlay View active.")
  (princ)
)
(defun c:ABOVERLAY () (SL_OverlayView))

;; Grouped visibility controls. Each group uses the first existing layer
;; as its state and then turns the complete group on or off together.
(defun SL_LayerExists (name) (if (tblsearch "LAYER" name) T nil))
(defun SL_LayerIsOn (name / data color)
  (setq data (tblsearch "LAYER" name))
  (if data
    (progn (setq color (cdr (assoc 62 data))) (or (null color) (> color 0)))
    nil
  )
)
(defun SL_FirstExistingLayer (layers / found)
  (setq found nil)
  (while (and layers (null found))
    (if (SL_LayerExists (car layers)) (setq found (car layers)))
    (setq layers (cdr layers))
  )
  found
)
(defun SL_SetLayerGroup (layers turnOn / layerName)
  (SL_SetLayer "0")
  (foreach layerName layers
    (if (SL_LayerExists layerName)
      (if turnOn (SL_LayerOn layerName) (SL_LayerOff layerName))
    )
  )
  (command "_.REGEN")
)
(defun SL_ToggleLayerGroup (label layers / stateLayer turnOn)
  (setq stateLayer (SL_FirstExistingLayer layers))
  (if stateLayer
    (progn
      (setq turnOn (not (SL_LayerIsOn stateLayer)))
      (SL_SetLayerGroup layers turnOn)
      (princ (strcat "\n" label (if turnOn " shown." " hidden.")))
    )
    (princ (strcat "\nNo " label " layers exist in this drawing."))
  )
  (princ)
)

(defun c:ABIMAGES () (SL_ToggleLayerGroup "Scan images" '("SCAN_IMAGES")))
(defun c:ABSCANS () (SL_ToggleLayerGroup "Scan outlines and labels" '("SCANS" "SCAN_TEXT")))
(defun c:ABHATCH () (SL_ToggleLayerGroup "Scan hatching" '("AUT_HATCH")))
(defun c:ABWELDS () (SL_ToggleLayerGroup "Welds and weld labels" '("CIRC_WELDS" "LONG_SEAMS" "CIRC_WELD_TEXT" "LONG_SEAM_TEXT")))
(defun c:ABNOZZLES () (SL_ToggleLayerGroup "Shell nozzles" '("NOZZLES" "SHELL_NOZZLE_TEXT")))
(defun c:ABOBJECTS () (SL_ToggleLayerGroup "Supports and objects" '("SUPPORTS" "SUPPORT_TEXT")))
(defun c:ABRULERS () (SL_ToggleLayerGroup "Rulers and references" '("X_AXIS" "Y_AXIS" "X_RULER_TEXT" "Y_RULER_TEXT")))
(defun c:ABHEADS () (SL_ToggleLayerGroup "Head views" '("HEADS" "HEAD_NOZZLE_TEXT" "HEAD_MUT_TEXT" "HEAD_TITLE_TEXT" "HEAD_CLOCK_TEXT")))
(defun c:ABINFO () (SL_ToggleLayerGroup "Legend and title block" '("LEGEND" "LEGEND_SAMPLE" "LEGEND_AUT_HATCH" "LEGEND_MUT_HATCH" "LEGEND_TEXT" "TITLE_BLOCK" "TITLE_BLOCK_TEXT")))

(defun SL_VisibilityMenuDisplay ()
  (princ "\n----------------------------------------")
  (princ "\n       AXISBUILDER VISIBILITY CONTROLS")
  (princ "\n----------------------------------------")
  (princ "\n  1  Show/Hide Scan Images")
  (princ "\n  2  Show/Hide Scan Outlines and Labels")
  (princ "\n  3  Show/Hide Scan Hatching")
  (princ "\n  4  Show/Hide Welds and Weld Labels")
  (princ "\n  5  Show/Hide Shell Nozzles")
  (princ "\n  6  Show/Hide Supports and Objects")
  (princ "\n  7  Show/Hide Rulers and References")
  (princ "\n  8  Show/Hide Head Views")
  (princ "\n  9  Show/Hide Legend and Title Block")
  (princ "\n  0  Back to Main Menu")
)
(defun c:ABVISIBILITY ( / choice done)
  (setq done nil)
  (while (not done)
    (SL_VisibilityMenuDisplay)
    (initget 4)
    (setq choice (getint "\nSelect visibility option [0-9] <0>: "))
    (if (null choice) (setq choice 0))
    (cond
      ((= choice 0) (setq done T))
      ((= choice 1) (c:ABIMAGES))
      ((= choice 2) (c:ABSCANS))
      ((= choice 3) (c:ABHATCH))
      ((= choice 4) (c:ABWELDS))
      ((= choice 5) (c:ABNOZZLES))
      ((= choice 6) (c:ABOBJECTS))
      ((= choice 7) (c:ABRULERS))
      ((= choice 8) (c:ABHEADS))
      ((= choice 9) (c:ABINFO))
      (T (princ "\nInvalid option. Enter a number from 0 through 9."))
    )
  )
  (princ)
)

;; One-drawing AXISBUILDER launcher.
(defun SL_ScanMenuDisplay ()
  (princ "\n========================================")
  (princ "\n              AXISBUILDER")
  (princ "\n========================================")
  (princ "\n  1  Generate Master Drawing")
  (princ "\n  2  Layout View")
  (princ "\n  3  Overlay View")
  (princ "\n  4  Visibility Controls")
  (princ "\n  5  Resize Generated Text")
  (princ "\n  6  Wrap Shell Nozzle")
  (princ "\n  7  Wrap Support/Object")
  (princ "\n  8  Create Letter-Size Section Sheets")
  (princ "\n  0  Exit")
)

(defun c:AXISBUILDER ( / choice done)
  (setq done nil)
  (while (not done)
    (SL_ScanMenuDisplay)
    (initget 4)
    (setq choice (getint "\nSelect command [0-8] <0>: "))
    (if (null choice) (setq choice 0))
    (cond
      ((= choice 0) (setq done T))
      ((= choice 1) (SL_RunMenuCommand 'c:AXISDRAWING "AXISDRAWING"))
      ((= choice 2) (SL_RunMenuCommand 'c:ABLAYOUT "ABLAYOUT"))
      ((= choice 3) (SL_RunMenuCommand 'c:ABOVERLAY "ABOVERLAY"))
      ((= choice 4) (SL_RunMenuCommand 'c:ABVISIBILITY "ABVISIBILITY"))
      ((= choice 5) (SL_RunMenuCommand 'c:TEXTRESIZE "TEXTRESIZE"))
      ((= choice 6) (SL_RunMenuCommand 'c:NOZZLEWRAP "NOZZLEWRAP"))
      ((= choice 7) (SL_RunMenuCommand 'c:OBJECTWRAP "OBJECTWRAP"))
      ((= choice 8) (SL_RunMenuCommand 'c:SECTIONPAGES "SECTIONPAGES"))
      (T (princ "\nInvalid option. Enter a number from 0 through 8."))
    )
  )
  (princ "\nAXISBUILDER closed.")
  (princ)
)

;; Backward-compatible alias for existing workflows.
(defun c:SCANMENU () (c:AXISBUILDER))

(princ "\nAxisBuilder v5.0 master drawing loaded. Type AXISBUILDER, or AXISDRAWING to generate directly.")
(princ)
